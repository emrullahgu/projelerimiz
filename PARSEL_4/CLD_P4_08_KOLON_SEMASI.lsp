;;; ==========================================================================
;;; CLD_P4_08_KOLON_SEMASI.lsp
;;; PARSEL 4 - KOLON SEMASI (TEK HAT DAGITIM SEMASI)
;;; Isveren : BROSCO ITHALAT IHRACAT VE TICARET ANONIM SIRKETI
;;; Konum   : ULUCAK / KEMALPASA / IZMIR
;;; Kaynak  : BROSCO 4 NOLU PARSEL MIMARI.dwg (mimari paftalar)
;;; Kullanim: APPLOAD ile yukleyin -> cizim otomatik olusur.
;;;          Yeniden cizmek icin komut: CLD_P4_KOLONSEMASI
;;;          Tum ciktilar "CLD-P4-KOL-*" katmanlarindadir; yeniden calistirmada bu katmanlar temizlenir.
;;;          Guvenlik uyarisi gelirse "Bir kez yukle" deyin veya klasoru Secenekler > Dosyalar >
;;;          Guvenilen Konumlar (TRUSTEDPATHS) listesine ekleyin.
;;; Uretici : CLD (Claude) otomatik muhendislik motoru - tum isimler CLD onekli.
;;;   Mimari: 2 kat, 31 mahal, kat kotlari ZK=+0.00, 1K=+3.50, bina yuksekligi 9.18 m
;;;   Elektrik: kurulu 388.1 kW, talep 253.6 kW, trafo 400 kVA, KMP 150 kVAr, jenerator 100 kVA
;;;   Aydinlatma: 316 armatur, 177 priz/cikis, 101 linye, 8 pano
;;;   Topraklama: R=0.78 ohm (birlesik), paratoner LPL II, 27 inis
;;;   Mekanik: VRF 80.0 kW ic unite, dis unite 68.0 kW
;;;   Sihhi: 36 armatur, 4 pis su kolonu, 29 yagmur inisi
;;; ==========================================================================

;;; ==========================================================================
;;; CLD CORE  -  ortak cizim altyapisi (katman, stil, varlik, tablo, oynatici)
;;; Tum isimler CLD onekli. ActiveX (vla-) kullanilmaz: AutoCAD / BricsCAD /
;;; accoreconsole uyumlu saf AutoLISP + entmake.
;;; Mimari paftalar WCS XZ duzleminde (ekstruzyon 0,-1,0) cizildiginden tum
;;; varliklar ayni duzlemde (*cld-ext*) uretilir; koordinatlar pafta (OCS)
;;; koordinatidir.
;;; ==========================================================================

(setq *cld-ver* "1.0")
(if (not *cld-ext*) (setq *cld-ext* '(0.0 0.0 1.0)))
(if (not *cld-u*) (setq *cld-u* 100.0))

;;; ---------------------------------------------------------------- yardimci
(defun cld:m (x) (* x *cld-u*))
(defun cld:3d (p) (list (float (car p)) (float (cadr p)) 0.0))
(defun cld:2d (p) (list (float (car p)) (float (cadr p))))
(defun cld:pxy (p dx dy) (list (+ (car p) dx) (+ (cadr p) dy)))
(defun cld:wcs (p) (trans (cld:3d p) *cld-ext* 0))
(defun cld:top (lay) (/= lay "0"))
(defun cld:x210 (lay) (if (cld:top lay) (list (cons 210 *cld-ext*) '(410 . "Model")) '()))
;; renk / cizgi tipi / kalinlik her zaman acik yazilir: cizimdeki CECOLOR / CELTYPE / CELWEIGHT ne olursa olsun
;; katmandan (ByLayer) gelir; blok icindekiler ByBlock
(defun cld:col (lay)
  (if (= lay "0") '((62 . 0) (6 . "ByBlock") (370 . -2)) '((62 . 256) (6 . "ByLayer") (370 . -1))))
(defun cld:dlen (s / n i)
  ;; gorunen karakter sayisi (\U+XXXX = 1 karakter)
  (setq n 0 i 1)
  (while (<= i (strlen s))
    (if (and (= (substr s i 3) "\\U+") (<= (+ i 6) (strlen s))) (setq i (+ i 7)) (setq i (1+ i)))
    (setq n (1+ n)))
  n)
(defun cld:maxl (l) (if l (apply 'max l) 0))
(defun cld:sum (l) (apply '+ (cons 0 l)))
(defun cld:nth-or (i l def) (if (and l (< i (length l))) (nth i l) def))
(defun cld:range (n / i r) (setq i (1- n)) (while (>= i 0) (setq r (cons i r) i (1- i))) r)

;;; ------------------------------------------------------ tablo kayitlari
(defun cld:ltype (nm desc dash gap / sc)
  (if (not (tblsearch "LTYPE" nm))
    (progn
      (setq sc (max 1e-6 (getvar "LTSCALE")))
      (entmake (list '(0 . "LTYPE") '(100 . "AcDbSymbolTableRecord") '(100 . "AcDbLinetypeTableRecord")
                     (cons 2 nm) '(70 . 0) (cons 3 desc) '(72 . 65) '(73 . 2)
                     (cons 40 (/ (+ dash gap) sc)) (cons 49 (/ dash sc)) '(74 . 0) (cons 49 (- (/ gap sc))) '(74 . 0)))))
  nm)
(defun cld:style ()
  (if (not (tblsearch "STYLE" "CLD_YAZI"))
    (entmake '((0 . "STYLE") (100 . "AcDbSymbolTableRecord") (100 . "AcDbTextStyleTableRecord")
               (2 . "CLD_YAZI") (70 . 0) (40 . 0.0) (41 . 0.85) (50 . 0.0) (71 . 0) (42 . 2.5)
               (3 . "arial.ttf") (4 . ""))))
  "CLD_YAZI")
(defun cld:lay (nm col lt lw / e ed)
  (if (not (tblsearch "LAYER" nm))
    (entmake (list '(0 . "LAYER") '(100 . "AcDbSymbolTableRecord") '(100 . "AcDbLayerTableRecord")
                   (cons 2 nm) '(70 . 0) (cons 62 col)
                   (cons 6 (if (and lt (tblsearch "LTYPE" lt)) lt "Continuous"))
                   (cons 370 lw)))
    (progn
      (setq e (tblobjname "LAYER" nm) ed (entget e))
      (setq ed (subst (cons 70 0) (assoc 70 ed) ed))
      (setq ed (subst (cons 62 col) (assoc 62 ed) ed))
      (if (and lt (tblsearch "LTYPE" lt) (assoc 6 ed)) (setq ed (subst (cons 6 lt) (assoc 6 ed) ed)))
      (if (assoc 370 ed) (setq ed (subst (cons 370 lw) (assoc 370 ed) ed)))
      (entmod ed)))
  nm)

;;; ---------------------------------------------------- varlik olusturucular
;;; lay "0" = blok tanimi icerigi (BYBLOCK renk, blok koordinati)
(defun cld:e-line (a b lay)
  (append (list '(0 . "LINE") (cons 8 lay)) (cld:col lay)
          (if (cld:top lay) (list (cons 10 (cld:wcs a)) (cons 11 (cld:wcs b))) (list (cons 10 (cld:3d a)) (cons 11 (cld:3d b))))
          (cld:x210 lay)))
(defun cld:e-circle (c r lay)
  (append (list '(0 . "CIRCLE") (cons 8 lay)) (cld:col lay) (list (cons 10 (cld:3d c)) (cons 40 r)) (cld:x210 lay)))
(defun cld:e-arc (c r a1 a2 lay)
  (append (list '(0 . "ARC") (cons 8 lay)) (cld:col lay) (list (cons 10 (cld:3d c)) (cons 40 r) (cons 50 a1) (cons 51 a2)) (cld:x210 lay)))
(defun cld:e-pl (pts closed w lay)
  (append (list '(0 . "LWPOLYLINE") '(100 . "AcDbEntity") (cons 8 lay)) (cld:col lay)
          (list '(100 . "AcDbPolyline") (cons 90 (length pts)) (cons 70 (+ (if closed 1 0) (if (cld:top lay) 128 0))) (cons 43 w) '(38 . 0.0))
          (mapcar '(lambda (p) (cons 10 (cld:2d p))) pts)
          (cld:x210 lay)))
(defun cld:e-dot (c r lay)
  (append (list '(0 . "LWPOLYLINE") '(100 . "AcDbEntity") (cons 8 lay)) (cld:col lay)
          (list '(100 . "AcDbPolyline") '(90 . 2) '(70 . 1) (cons 43 r) '(38 . 0.0)
                (cons 10 (list (- (car c) (/ r 2.0)) (cadr c))) '(42 . 1.0)
                (cons 10 (list (+ (car c) (/ r 2.0)) (cadr c))) '(42 . 1.0))
          (cld:x210 lay)))
(defun cld:e-solid (p1 p2 p3 p4 lay)
  (append (list '(0 . "SOLID") (cons 8 lay)) (cld:col lay)
          (list (cons 10 (cld:3d p1)) (cons 11 (cld:3d p2)) (cons 12 (cld:3d p4)) (cons 13 (cld:3d p3)))
          (cld:x210 lay)))
(defun cld:e-text (p h s j lay / ed p3)
  ;; j: 0 sol-taban, 1 orta-taban, 2 sag-taban, 4 orta-orta, 7 sol-orta, 9 sag-orta
  (setq p3 (cld:3d p))
  (setq ed (append (list '(0 . "TEXT") (cons 8 lay)) (cld:col lay)
                   (list (cons 7 (cld:style)) (cons 10 p3) (cons 40 h) (cons 1 s) '(50 . 0.0) '(41 . 0.85))))
  (setq ed (cond ((= j 1) (append ed (list '(72 . 1) (cons 11 p3) '(73 . 0))))
                 ((= j 2) (append ed (list '(72 . 2) (cons 11 p3) '(73 . 0))))
                 ((= j 4) (append ed (list '(72 . 1) (cons 11 p3) '(73 . 2))))
                 ((= j 7) (append ed (list '(72 . 0) (cons 11 p3) '(73 . 2))))
                 ((= j 9) (append ed (list '(72 . 2) (cons 11 p3) '(73 . 2))))
                 (T ed)))
  (append ed (cld:x210 lay)))
(defun cld:e-ins (blk p sc rot lay)
  (append (list '(0 . "INSERT") (cons 8 lay)) (cld:col lay) (list (cons 2 blk) (cons 10 (cld:3d p))
                (cons 41 sc) (cons 42 sc) (cons 43 sc) (cons 50 rot))
          (cld:x210 lay)))
(defun cld:line (a b lay) (entmake (cld:e-line a b lay)))
(defun cld:pl (pts closed w lay) (if (cdr pts) (entmake (cld:e-pl pts closed w lay))))
(defun cld:txt (p h s j lay) (entmake (cld:e-text p h s j lay)))
(defun cld:rect (p1 p2 lay) (cld:pl (list p1 (list (car p2) (cadr p1)) p2 (list (car p1) (cadr p2))) T 0.0 lay))

;;; ------------------------------------------------------------ blok tanimi
(defun cld:defblk (name ents)
  (if (not (tblsearch "BLOCK" name))
    (progn
      (entmake (list '(0 . "BLOCK") (cons 2 name) '(70 . 0) '(10 0.0 0.0 0.0) '(8 . "0")))
      (foreach e ents (entmake e))
      (entmake '((0 . "ENDBLK") (8 . "0")))))
  name)

;;; mimari altlik blogu: plines ((kapali (x y) (x y) ...) ...)  texts ((x y h "yazi") ...)
(defun cld:defblk-bg (name plines texts)
  (if (not (tblsearch "BLOCK" name))
    (progn
      (entmake (list '(0 . "BLOCK") (cons 2 name) '(70 . 0) '(10 0.0 0.0 0.0) '(8 . "0")))
      (foreach p plines (if (cddr p) (entmake (cld:e-pl (cdr p) (car p) 0.0 "0"))))
      (foreach s texts (entmake (cld:e-text (list (car s) (cadr s)) (caddr s) (cadddr s) 4 "0")))
      (entmake '((0 . "ENDBLK") (8 . "0")))))
  name)

;;; ------------------------------------------------------------------ tablo
;;; rows: ((hucre ...) ...)  ilk satir baslik. Sutun genislikleri otomatik.
(defun cld:table (org title rows h lay / ncol widths rh y x w i r cw tw pad s)
  (setq pad (* 0.6 h) rh (* 2.0 h))
  (setq ncol (cld:maxl (mapcar 'length rows)))
  (setq widths (mapcar '(lambda (c)
                          (+ (* 2 pad) (* 0.66 h (cld:maxl (mapcar '(lambda (r) (cld:dlen (cld:nth-or c r ""))) rows)))))
                       (cld:range ncol)))
  (setq tw (cld:sum widths) x (car org) y (cadr org))
  (if (and title (/= title ""))
    (progn
      (cld:rect (list x y) (list (+ x tw) (- y (* 1.5 rh))) lay)
      (cld:txt (list (+ x pad) (- y (* 0.75 rh))) (* 1.3 h) title 7 lay)
      (setq y (- y (* 1.5 rh)))))
  (setq i 0)
  (foreach r rows
    (setq x (car org) cw 0)
    (cld:rect (list x y) (list (+ x tw) (- y rh)) lay)
    (foreach w widths
      (if (> cw 0) (cld:line (list x y) (list x (- y rh)) lay))
      (setq s (cld:nth-or cw r ""))
      (if (/= s "") (cld:txt (list (+ x pad) (- y (* 0.5 rh))) h s 7 lay))
      (setq x (+ x w) cw (1+ cw)))
    (if (= i 0) (cld:pl (list (list (car org) (- y rh)) (list (+ (car org) tw) (- y rh))) nil (* 0.12 h) lay))
    (setq y (- y rh) i (1+ i)))
  (list (- y (* 2.0 h)) tw))
(defun cld:notes (org title lines h lay / y)
  (setq y (cadr org))
  (if (and title (/= title "")) (progn (cld:txt (list (car org) y) (* 1.3 h) title 0 lay) (setq y (- y (* 2.2 h)))))
  (foreach s lines (cld:txt (list (car org) y) h s 0 lay) (setq y (- y (* 1.7 h))))
  (- y h))

;;; ------------------------------------------------------------- oynatici
;;; Hesap motorunun urettigi cizim komutlari:
;;;  ("LY" ad renk cizgitipi kalinlik)        katman
;;;  ("I" lay blok x y aci olcek)             sembol (olcek * *cld-u*)
;;;  ("L" lay x1 y1 x2 y2)                    cizgi
;;;  ("P" lay kapali genislik ((x y) ...))    polyline
;;;  ("C" lay x y r)                          daire
;;;  ("D" lay x y r)                          dolu daire
;;;  ("T" lay x y h hiza "yazi")              yazi
;;;  ("TB" lay x y h "baslik" satirlar)       tablo
;;;  ("NT" lay x y h "baslik" satirlar)       not blogu
(defun cld:op (o / k)
  (setq k (car o))
  (cond ((= k "I") (entmake (cld:e-ins (nth 2 o) (list (nth 3 o) (nth 4 o)) (* (nth 6 o) *cld-u*) (nth 5 o) (nth 1 o))))
        ((= k "L") (cld:line (list (nth 2 o) (nth 3 o)) (list (nth 4 o) (nth 5 o)) (nth 1 o)))
        ((= k "P") (cld:pl (nth 4 o) (nth 2 o) (nth 3 o) (nth 1 o)))
        ((= k "C") (entmake (cld:e-circle (list (nth 2 o) (nth 3 o)) (nth 4 o) (nth 1 o))))
        ((= k "D") (entmake (cld:e-dot (list (nth 2 o) (nth 3 o)) (nth 4 o) (nth 1 o))))
        ((= k "T") (cld:txt (list (nth 2 o) (nth 3 o)) (nth 4 o) (nth 6 o) (nth 5 o) (nth 1 o)))
        ((= k "TB") (cld:table (list (nth 2 o) (nth 3 o)) (nth 5 o) (nth 6 o) (nth 4 o) (nth 1 o)))
        ((= k "NT") (cld:notes (list (nth 2 o) (nth 3 o)) (nth 5 o) (nth 6 o) (nth 4 o) (nth 1 o)))
        ((= k "LY") (cld:lay (nth 1 o) (nth 2 o) (nth 3 o) (nth 4 o)))
        ((= k "BK") (cld:defblk-bg (nth 1 o) (nth 2 o) (nth 3 o)))))
(defun cld:play (ops / r)
  (foreach o ops
    (setq r (vl-catch-all-apply 'cld:op (list o)))
    (cond ((vl-catch-all-error-p r) (setq *cld-bad* (cons (list (car o) (nth 1 o) (vl-catch-all-error-message r)) *cld-bad*)))
          ((and (null r) (or (member (car o) '("I" "L" "C" "D" "T")) (and (= (car o) "P") (cdr (nth 4 o)))))
           (setq *cld-bad* (cons (list (car o) (nth 1 o) (if (= (car o) "I") (nth 2 o) "")) *cld-bad*)))
          (T (setq *cld-n* (1+ *cld-n*))))))

;;; ------------------------------------------------------- calisma ortami
(defun cld:clear (pat / ss i n)
  (setq n 0)
  (if (setq ss (ssget "_X" (list (cons 8 pat))))
    (progn (setq i 0) (while (< i (sslength ss)) (entdel (ssname ss i)) (setq i (1+ i) n (1+ n)))))
  n)
(defun cld:begin (pat)
  (setq *cld-old* (list (getvar "CMDECHO") (getvar "OSMODE")) *cld-n* 0 *cld-bad* nil)
  (setvar "CMDECHO" 0)
  (setvar "OSMODE" 0)
  ;; cizim model alaninda olusur (bir yerlesim sekmesi acik olsa bile)
  (if (= 0 (getvar "TILEMODE")) (vl-catch-all-apply 'setvar (list "TILEMODE" 1)))
  (vl-catch-all-apply 'command-s (list "_.UNDO" "_BEGIN"))
  (cld:style)
  (cld:ltype "CLD_KESIK" "CLD kesik __ __" (cld:m 0.30) (cld:m 0.15))
  (cld:ltype "CLD_NOKTALI" "CLD noktali . . ." (cld:m 0.05) (cld:m 0.10))
  (cld:ltype "CLD_UZUNKESIK" "CLD uzun kesik ____ ____" (cld:m 0.80) (cld:m 0.20)))
;;; disiplin katmanlarinin kilidini kaldir / coz (eski cikti silinebilsin)
(defun cld:unlock (pat / tl ed)
  (setq tl (tblnext "LAYER" T))
  (while tl
    (if (and (wcmatch (cdr (assoc 2 tl)) pat) (/= 0 (logand 5 (cdr (assoc 70 tl)))))
      (progn (setq ed (entget (tblobjname "LAYER" (cdr (assoc 2 tl)))))
             (entmod (subst (cons 70 0) (assoc 70 ed) ed))))
    (setq tl (tblnext "LAYER"))))
(defun cld:restore ()
  (vl-catch-all-apply 'command-s (list "_.UNDO" "_END"))
  (if *cld-old* (progn (setvar "CMDECHO" (car *cld-old*)) (setvar "OSMODE" (cadr *cld-old*))))
  (setq *cld-old* nil))
(defun cld:first5 (l / r i) (setq i 0) (foreach x l (if (< i 5) (setq r (cons x r))) (setq i (1+ i))) (reverse r))
(defun cld:end (msg)
  (cld:restore)
  (princ (strcat "\n" msg " (" (itoa *cld-n*) " varlik/komut)"))
  (if *cld-bad*
    (progn
      (princ (strcat "\nCLD UYARI: " (itoa (length *cld-bad*)) " varlik olusturulamadi, ilkleri:"))
      (foreach b (cld:first5 (reverse *cld-bad*)) (princ (strcat "\n   " (vl-princ-to-string b))))))
  (princ))
;;; acik cizim baska bir parsele mi ait? (dosya adinda baska parselin "<n> NOLU" ifadesi)
(defun cld:wrong-dwg (parcel others / nm bad)
  (setq nm (strcase (getvar "DWGNAME")))
  (foreach o others (if (wcmatch nm (strcat "* " o " NOLU*,BROSCO " o " *,P" o ".DWG")) (setq bad T)))
  (and bad (not (wcmatch nm (strcat "* " parcel " NOLU*,BROSCO " parcel " *,P" parcel ".DWG")))))
(defun cld:err (m)
  (cld:restore)
  (if (not (member m '("Function cancelled" "quit / exit abort"))) (princ (strcat "\nCLD HATA: " m)))
  (princ))


;;; ==========================================================================
;;; CLD SEMBOL KUTUPHANESI - bloklar 1 birim = 1 m tanimlanir, cizime
;;; (olcek x *cld-u*) ile yerlestirilir. Duvar sembollerinde duvar yerel x=0,
;;; sembol +X yonune (mahal icine) bakar.
;;; ==========================================================================

(defun cld:b-box (w h)
  (cld:e-pl (list (list (- (/ w 2)) (- (/ h 2))) (list (/ w 2) (- (/ h 2))) (list (/ w 2) (/ h 2)) (list (- (/ w 2)) (/ h 2))) T 0.0 "0"))
(defun cld:b-wallbox (d w)
  (cld:e-pl (list (list 0.0 (- (/ w 2))) (list d (- (/ w 2))) (list d (/ w 2)) (list 0.0 (/ w 2))) T 0.0 "0"))
(defun cld:b-x (r)
  (list (cld:e-line (list (- r) (- r)) (list r r) "0") (cld:e-line (list (- r) r) (list r (- r)) "0")))
(defun cld:b-txt (p h s) (cld:e-text p h s 4 "0"))

(defun cld:def-symbols ( / r)
  ;; ---------------- AYDINLATMA
  (setq r 0.12)
  (cld:defblk "CLD_S_DL" (append (list (cld:e-circle '(0 0) r "0")) (cld:b-x (* r 0.707))))
  (cld:defblk "CLD_S_DLB" (append (list (cld:e-circle '(0 0) r "0") (cld:e-circle '(0 0) (* r 1.35) "0")) (cld:b-x (* r 0.707))))
  (cld:defblk "CLD_S_HB" (append (list (cld:e-circle '(0 0) 0.30 "0") (cld:e-circle '(0 0) 0.12 "0")) (cld:b-x 0.21)))
  (cld:defblk "CLD_S_PNL" (append (list (cld:b-box 0.6 0.6)) (cld:b-x 0.3)))
  (cld:defblk "CLD_S_ETJ" (list (cld:b-box 1.2 0.2) (cld:e-line '(-0.6 0.0) '(0.6 0.0) "0")
                                (cld:e-line '(-0.5 -0.1) '(-0.5 0.1) "0") (cld:e-line '(0.5 -0.1) '(0.5 0.1) "0")))
  (cld:defblk "CLD_S_PLF" (list (cld:e-circle '(0 0) 0.15 "0") (cld:e-dot '(0 0) 0.07 "0")))
  (cld:defblk "CLD_S_ACIL" (list (cld:b-box 0.32 0.16) (cld:e-solid '(-0.16 -0.08) '(0.16 -0.08) '(0.16 0.08) '(0.16 0.08) "0")))
  (cld:defblk "CLD_S_EXIT" (list (cld:b-box 0.40 0.20) (cld:e-line '(-0.14 0) '(0.12 0) "0") (cld:e-line '(0.12 0) '(0.04 0.06) "0")
                                 (cld:e-line '(0.12 0) '(0.04 -0.06) "0")))
  (cld:defblk "CLD_S_PRJ" (list (cld:e-pl '((-0.15 -0.10) (0.15 -0.10) (0.22 0.12) (-0.22 0.12)) T 0.0 "0") (cld:e-line '(-0.15 0.0) '(0.15 0.0) "0")))
  (cld:defblk "CLD_S_BOLLARD" (list (cld:e-circle '(0 0) 0.12 "0") (cld:e-dot '(0 0) 0.12 "0")))
  ;; ---------------- PRIZ / ANAHTAR (duvar sembolleri)
  (cld:defblk "CLD_S_PRIZ" (list (cld:e-line '(0 0) '(0.06 0) "0") (cld:e-line '(0.06 -0.12) '(0.06 0.12) "0")
                                 (cld:e-arc '(0.06 0) 0.12 (- (/ pi 2)) (/ pi 2) "0") (cld:e-line '(0.20 -0.10) '(0.20 0.10) "0")))
  (cld:defblk "CLD_S_PRIZE" (list (cld:e-line '(0 0) '(0.06 0) "0") (cld:e-line '(0.06 -0.12) '(0.06 0.12) "0")
                                  (cld:e-arc '(0.06 0) 0.12 (- (/ pi 2)) (/ pi 2) "0") (cld:e-dot '(0.11 0) 0.06 "0")
                                  (cld:e-line '(0.20 -0.10) '(0.20 0.10) "0")))
  (cld:defblk "CLD_S_PRIZU" (list (cld:e-line '(0 0) '(0.06 0) "0") (cld:e-line '(0.06 -0.12) '(0.06 0.12) "0")
                                  (cld:e-arc '(0.06 0) 0.12 (- (/ pi 2)) (/ pi 2) "0") (cld:b-txt '(0.11 0) 0.09 "U")))
  (cld:defblk "CLD_S_PRIZ3" (list (cld:e-line '(0 0) '(0.06 0) "0") (cld:e-line '(0.06 -0.14) '(0.06 0.14) "0")
                                  (cld:e-arc '(0.06 0) 0.14 (- (/ pi 2)) (/ pi 2) "0")
                                  (cld:e-line '(0.10 -0.06) '(0.18 -0.06) "0") (cld:e-line '(0.10 0.0) '(0.18 0.0) "0") (cld:e-line '(0.10 0.06) '(0.18 0.06) "0")))
  (cld:defblk "CLD_S_PGRUP" (list (cld:b-box 0.50 0.30) (cld:e-arc '(-0.13 -0.02) 0.08 0.0 pi "0") (cld:e-arc '(0.0 -0.02) 0.08 0.0 pi "0")
                                  (cld:e-arc '(0.13 -0.02) 0.08 0.0 pi "0") (cld:e-line '(-0.25 -0.08) '(0.25 -0.08) "0")))
  (foreach c '(("CLD_S_CK_KLIMA" "K") ("CLD_S_CK_FIRIN" "F") ("CLD_S_CK_BULASIK" "B") ("CLD_S_CK_CAMASIR" "\\U+00C7")
               ("CLD_S_CK_KURUTMA" "KM") ("CLD_S_CK_KOMBI" "KB") ("CLD_S_CK_DAVLUMBAZ" "D") ("CLD_S_CK_POMPA" "P")
               ("CLD_S_CK_ASPIRATOR" "A") ("CLD_S_CK_ASANSOR" "AS") ("CLD_S_CK_SARJ" "EV") ("CLD_S_CK_ISITICI" "IS")
               ("CLD_S_CK_TERMOSIFON" "TS") ("CLD_S_CK_MAKINE" "M"))
    (cld:defblk (car c) (list (cld:b-wallbox 0.24 0.24) (cld:e-solid '(0 -0.12) '(0.08 -0.12) '(0.08 0.12) '(0 0.12) "0")
                              (cld:b-txt '(0.16 0.0) 0.09 (cadr c)))))
  (cld:defblk "CLD_S_ANH1" (list (cld:e-circle '(0.10 0) 0.05 "0") (cld:e-line '(0.135 0.035) '(0.25 0.15) "0") (cld:e-line '(0.25 0.15) '(0.29 0.11) "0")))
  (cld:defblk "CLD_S_ANH2" (list (cld:e-circle '(0.10 0) 0.05 "0") (cld:e-line '(0.135 0.035) '(0.25 0.15) "0") (cld:e-line '(0.25 0.15) '(0.29 0.11) "0")
                                 (cld:e-line '(0.135 -0.035) '(0.25 -0.15) "0") (cld:e-line '(0.25 -0.15) '(0.29 -0.11) "0")))
  (cld:defblk "CLD_S_VAV" (list (cld:e-circle '(0.10 0) 0.05 "0") (cld:e-line '(0.135 0.035) '(0.25 0.15) "0") (cld:e-line '(0.25 0.15) '(0.29 0.11) "0")
                                (cld:e-line '(0.065 -0.035) '(-0.05 -0.15) "0") (cld:e-line '(-0.05 -0.15) '(-0.09 -0.11) "0")))
  (cld:defblk "CLD_S_BUAT" (list (cld:e-circle '(0 0) 0.05 "0")))
  ;; ---------------- PANOLAR
  (cld:defblk "CLD_S_TP" (list (cld:b-wallbox 0.16 0.50) (cld:e-solid '(0 -0.25) '(0.16 -0.25) '(0.16 0.25) '(0 -0.25) "0")))
  (cld:defblk "CLD_S_ADP" (list (cld:b-wallbox 0.30 0.90) (cld:e-solid '(0 -0.45) '(0.30 -0.45) '(0.30 0.45) '(0 0.45) "0")))
  (cld:defblk "CLD_S_KMP" (list (cld:b-wallbox 0.30 0.60) (cld:e-line '(0 -0.30) '(0.30 0.30) "0") (cld:b-txt '(0.15 -0.15) 0.10 "C")))
  (cld:defblk "CLD_S_KOLON" (list (cld:e-circle '(0 0) 0.15 "0") (cld:e-line '(-0.106 -0.106) '(0.106 0.106) "0")
                                  (cld:e-line '(0.106 0.106) '(0.02 0.106) "0") (cld:e-line '(0.106 0.106) '(0.106 0.02) "0")))
  (cld:defblk "CLD_S_OAP" (list (cld:b-wallbox 0.20 0.60) (cld:e-solid '(0 -0.30) '(0.20 -0.30) '(0.20 0.0) '(0 0.0) "0")))
  (cld:defblk "CLD_S_TRAFO" (list (cld:b-box 6.0 5.0) (cld:e-circle '(-0.45 0) 0.8 "0") (cld:e-circle '(0.45 0) 0.8 "0")))
  (cld:defblk "CLD_S_JEN" (list (cld:b-box 4.0 1.6) (cld:e-circle '(-1.2 0) 0.55 "0") (cld:b-txt '(-1.2 0) 0.5 "G")))
  ;; ---------------- TOPRAKLAMA / PARATONER
  (cld:defblk "CLD_S_TOP_FILIZ" (list (cld:e-circle '(0 0) 0.15 "0") (cld:e-dot '(0 0) 0.12 "0")))
  (cld:defblk "CLD_S_TOP_EPB" (list (cld:b-box 0.60 0.16) (cld:e-solid '(-0.30 -0.08) '(0.30 -0.08) '(0.30 0.08) '(-0.30 0.08) "0")
                                    (cld:e-line '(-0.2 -0.08) '(-0.2 -0.25) "0") (cld:e-line '(0 -0.08) '(0 -0.25) "0") (cld:e-line '(0.2 -0.08) '(0.2 -0.25) "0")))
  (cld:defblk "CLD_S_TOP_YEB" (list (cld:b-wallbox 0.10 0.30) (cld:e-solid '(0 -0.15) '(0.10 -0.15) '(0.10 0.15) '(0 0.15) "0")))
  (cld:defblk "CLD_S_TOP_KAZIK" (list (cld:e-line '(0 0.20) '(0 0) "0") (cld:e-line '(-0.15 0) '(0.15 0) "0")
                                      (cld:e-line '(-0.10 -0.05) '(0.10 -0.05) "0") (cld:e-line '(-0.05 -0.10) '(0.05 -0.10) "0")
                                      (cld:e-circle '(0 0.05) 0.25 "0")))
  (cld:defblk "CLD_S_TOP_OLCU" (append (list (cld:b-box 0.30 0.30)) (cld:b-x 0.15)))
  (cld:defblk "CLD_S_PAR_UC" (list (cld:e-circle '(0 0) 0.20 "0") (cld:e-solid '(-0.12 -0.08) '(0.12 -0.08) '(0.0 0.14) '(0.0 0.14) "0")))
  (cld:defblk "CLD_S_PAR_INIS" (list (cld:e-circle '(0 0) 0.15 "0") (cld:e-dot '(0 0) 0.08 "0")
                                     (cld:e-line '(0.0 -0.15) '(0.0 -0.40) "0") (cld:e-line '(-0.08 -0.30) '(0.0 -0.40) "0") (cld:e-line '(0.08 -0.30) '(0.0 -0.40) "0")))
  (cld:defblk "CLD_S_PAR_KLEMENS" (list (cld:b-box 0.25 0.25) (cld:e-solid '(-0.125 -0.125) '(0.125 -0.125) '(0.125 0.125) '(-0.125 -0.125) "0")))
  ;; ---------------- MEKANIK
  (cld:defblk "CLD_S_KASET" (append (list (cld:b-box 0.84 0.84) (cld:b-box 0.56 0.56)) (cld:b-x 0.28)))
  (cld:defblk "CLD_S_VRFOUT" (list (cld:b-box 1.30 0.75) (cld:e-circle '(-0.3 0) 0.28 "0") (cld:e-circle '(0.3 0) 0.28 "0")))
  (cld:defblk "CLD_S_HRV" (list (cld:b-box 1.40 0.80) (cld:e-line '(-0.7 -0.4) '(0.7 0.4) "0") (cld:e-line '(-0.7 0.4) '(0.7 -0.4) "0") (cld:b-txt '(0 0.25) 0.15 "HRV")))
  (cld:defblk "CLD_S_MENFEZ" (append (list (cld:b-box 0.60 0.60) (cld:b-box 0.30 0.30)) (cld:b-x 0.30)))
  (cld:defblk "CLD_S_EMIS" (list (cld:b-box 0.40 0.40) (cld:e-line '(-0.2 -0.1) '(0.2 -0.1) "0") (cld:e-line '(-0.2 0.0) '(0.2 0.0) "0") (cld:e-line '(-0.2 0.1) '(0.2 0.1) "0")))
  (cld:defblk "CLD_S_CATIFAN" (list (cld:e-circle '(0 0) 0.60 "0") (cld:e-circle '(0 0) 0.15 "0") (cld:e-line '(0 0) '(0.5 0.25) "0")
                                    (cld:e-line '(0 0) '(-0.5 0.25) "0") (cld:e-line '(0 0) '(0 -0.55) "0")))
  (cld:defblk "CLD_S_PANJUR" (list (cld:b-wallbox 0.20 1.20) (cld:e-line '(0 -0.4) '(0.2 -0.3) "0") (cld:e-line '(0 0.0) '(0.2 0.1) "0") (cld:e-line '(0 0.4) '(0.2 0.5) "0")))
  (cld:defblk "CLD_S_RADYANT" (list (cld:e-pl '((-3.0 -0.15) (3.0 -0.15) (3.0 0.15) (-3.0 0.15)) T 0.0 "0") (cld:e-line '(-3.0 0) '(2.6 0) "0") (cld:b-box 0.6 0.4)))
  (cld:defblk "CLD_S_SIGFAN" (list (cld:b-box 0.80 0.60) (cld:e-circle '(0 0) 0.22 "0") (cld:b-txt '(0 -0.2) 0.10 "S")))
  ;; ---------------- SIHHI TESISAT
  (cld:defblk "CLD_S_PK" (append (list (cld:e-circle '(0 0) 0.10 "0")) (cld:b-x 0.07)))
  (cld:defblk "CLD_S_TSK" (list (cld:e-circle '(0 0) 0.08 "0") (cld:e-dot '(0 0) 0.05 "0")))
  (cld:defblk "CLD_S_YK" (list (cld:e-circle '(0 0) 0.10 "0") (cld:e-circle '(0 0) 0.05 "0")))
  (cld:defblk "CLD_S_YS" (list (cld:b-box 0.18 0.18) (cld:e-circle '(0 0) 0.06 "0") (cld:e-line '(-0.06 0) '(0.06 0) "0")))
  (cld:defblk "CLD_S_SUSAYAC" (list (cld:e-circle '(0 0) 0.12 "0") (cld:e-line '(-0.12 0) '(0.12 0) "0") (cld:b-txt '(0 0.05) 0.06 "m3")))
  (cld:defblk "CLD_S_ROGAR" (list (cld:b-box 0.60 0.60) (cld:e-circle '(0 0) 0.22 "0")))
  (cld:defblk "CLD_S_DEPO" (append (list (cld:b-box 1.20 0.80)) (list (cld:e-line '(-0.6 -0.4) '(0.6 0.4) "0") (cld:e-line '(-0.6 0.4) '(0.6 -0.4) "0"))))
  (cld:defblk "CLD_S_KLOZET" (list (cld:e-pl '((-0.18 0.30) (0.18 0.30) (0.18 0.12) (-0.18 0.12)) T 0.0 "0")
                                   (cld:e-circle '(0 -0.08) 0.18 "0")))
  (cld:defblk "CLD_S_LAVABO" (list (cld:b-box 0.50 0.40) (cld:e-circle '(0 -0.03) 0.13 "0")))
  (cld:defblk "CLD_S_ABDEST" (list (cld:b-box 0.40 0.30) (cld:e-circle '(0 0.05) 0.05 "0") (cld:e-line '(0 0.05) '(0 -0.12) "0")))
  (cld:defblk "CLD_S_YD" (list (cld:b-wallbox 0.25 0.80) (cld:e-solid '(0 -0.40) '(0.25 -0.40) '(0.25 -0.10) '(0 -0.10) "0")
                              (cld:b-txt '(0.125 0.15) 0.12 "YD")))
  (cld:defblk "CLD_S_DUS" (append (list (cld:b-box 0.90 0.90) (cld:e-circle '(0 0) 0.06 "0")) (cld:b-x 0.45)))
  T)


(setq *cld-u* 100.0)
(setq *cld-ext* (list 0.0 0.0 1.0))

(defun cld:ops-p4_kolon_semasi-layers () (cld:play (quote (("LY" "CLD-P4-KOL-YAZI" 7 nil -3) ("LY" "CLD-P4-KOL-PAFTA" 7 nil 50) ("LY" "CLD-P4-KOL-ALTLIK" 8 nil 13) ("LY" "CLD-P4-KOL-SEMA" 7 nil 35) ("LY" "CLD-P4-KOL-KAT" 8 "CLD_KESIK" 18)))))
(defun cld:ops-p4_kolon_semasi-1 () (cld:play (quote (
   ("T" "CLD-P4-KOL-YAZI" 224247.9 86390.2 160.0 0 "PARSEL 4 - KOLON \\U+015EEMASI (TEK HAT DA\\U+011EITIM \\U+015EEMASI)")
   ("T" "CLD-P4-KOL-YAZI" 224247.9 86160.2 50.0 0 "BROSCO \\U+0130THALAT \\U+0130HRACAT VE T\\U+0130CARET ANON\\U+0130M \\U+015E\\U+0130RKET\\U+0130 - ULUCAK / KEMALPA\\U+015EA / \\U+0130ZM\\U+0130R")
   ("T" "CLD-P4-KOL-YAZI" 224247.9 86080.2 38.0 0 "CLD otomatik proje  |  Disiplin 08  |  19.10.2026  |  Paftalar 1/100  |  Katman \\U+00F6neki CLD-P4-KOL-*")
   ("L" "CLD-P4-KOL-KAT" 224247.9 77640.2 250247.9 77640.2)
   ("T" "CLD-P4-KOL-YAZI" 224297.9 77700.2 45.0 0 "ZEM\\U+0130N KAT  (\\U+00B10,00 m)")
   ("L" "CLD-P4-KOL-KAT" 224247.9 82640.2 250247.9 82640.2)
   ("T" "CLD-P4-KOL-YAZI" 224297.9 82700.2 45.0 0 "1. KAT  (+3,50 m)")
   ("L" "CLD-P4-KOL-KAT" 224247.9 85240.2 250247.9 85240.2)
   ("P" "CLD-P4-KOL-SEMA" T 4.0 ((225197.9 79040.2) (226897.9 79040.2) (226897.9 79640.2) (225197.9 79640.2)))
   ("T" "CLD-P4-KOL-YAZI" 226047.9 79570.2 32.0 1 "TRAFO")
   ("T" "CLD-P4-KOL-YAZI" 226047.9 79520.2 25.0 1 "400 kVA 34,5/0,4 kV")
   ("T" "CLD-P4-KOL-YAZI" 226047.9 79470.2 25.0 1 "Dyn11 uk=%4")
   ("P" "CLD-P4-KOL-SEMA" T 4.0 ((225197.9 80065.2) (226897.9 80065.2) (226897.9 80515.2) (225197.9 80515.2)))
   ("T" "CLD-P4-KOL-YAZI" 226047.9 80445.2 32.0 1 "JENERAT\\U+00D6R")
   ("T" "CLD-P4-KOL-YAZI" 226047.9 80395.2 25.0 1 "100 kVA")
   ("P" "CLD-P4-KOL-SEMA" T 4.0 ((228447.9 78990.2) (231247.9 78990.2) (231247.9 80290.2) (228447.9 80290.2)))
   ("T" "CLD-P4-KOL-YAZI" 229847.9 80220.2 32.0 1 "ADP")
   ("T" "CLD-P4-KOL-YAZI" 229847.9 80170.2 25.0 1 "ANA DA\\U+011EITIM PANOSU")
   ("T" "CLD-P4-KOL-YAZI" 229847.9 80120.2 25.0 1 "Ana \\U+015Falter 630 A + toroid KAKR")
   ("T" "CLD-P4-KOL-YAZI" 229847.9 80070.2 25.0 1 "Ik \\U+2248 14,4 kA")
   ("T" "CLD-P4-KOL-YAZI" 229847.9 80020.2 25.0 1 "SPD Tip 1+2, analiz\\U+00F6r, ATS")
   ("T" "CLD-P4-KOL-YAZI" 229847.9 79970.2 25.0 1 "Kurulu 388,05 kW")
   ("T" "CLD-P4-KOL-YAZI" 229847.9 79920.2 25.0 1 "Talep 253,61 kW")
   ("L" "CLD-P4-KOL-SEMA" 226897.9 79340.2 228447.9 79340.2)
   ("T" "CLD-P4-KOL-YAZI" 226947.9 79380.2 22.0 0 "3 x (NYY 3x240+120 + 1x120 PE) mm\\U+00B2 - her hatta ayr\\U+0131 PE")
   ("L" "CLD-P4-KOL-SEMA" 226897.9 80290.2 228447.9 79940.2)
   ("T" "CLD-P4-KOL-YAZI" 226947.9 80330.2 22.0 0 "jenerat\\U+00F6r \\U+2192 ATS (acil bara)")
   ("P" "CLD-P4-KOL-SEMA" T 4.0 ((228947.9 78365.2) (230747.9 78365.2) (230747.9 78815.2) (228947.9 78815.2)))
   ("T" "CLD-P4-KOL-YAZI" 229847.9 78745.2 32.0 1 "KMP")
   ("T" "CLD-P4-KOL-YAZI" 229847.9 78695.2 25.0 1 "Kompanzasyon 150 kVAr")
   ("L" "CLD-P4-KOL-SEMA" 229847.9 78990.2 229847.9 78815.2)
   ("L" "CLD-P4-KOL-SEMA" 227047.9 79040.2 227047.9 78440.2)
   ("P" "CLD-P4-KOL-SEMA" T 4.0 ((226197.9 77840.2) (227897.9 77840.2) (227897.9 78440.2) (226197.9 78440.2)))
   ("T" "CLD-P4-KOL-YAZI" 227047.9 78370.2 32.0 1 "YPP")
   ("T" "CLD-P4-KOL-YAZI" 227047.9 78320.2 25.0 1 "YANGIN POMPA PANOSU")
   ("T" "CLD-P4-KOL-YAZI" 227047.9 78270.2 25.0 1 "TS-YP \\U+015Febeke / jenerat\\U+00F6r")
   ("T" "CLD-P4-KOL-YAZI" 227047.9 78220.2 25.0 1 "aM sigorta 32 A (ana \\U+015Falter \\U+00F6ncesi), KAKR yok (yaln\\U+0131z alarm)")
   ("T" "CLD-P4-KOL-YAZI" 227047.9 78170.2 25.0 1 "NHXH-FE180/E90 5x10 mm\\U+00B2")
   ("T" "CLD-P4-KOL-YAZI" 227107.9 78840.2 20.0 0 "ana \\U+015Falter \\U+00F6ncesi (KAKR yok)")
   ("P" "CLD-P4-KOL-SEMA" nil 4.0 ((225197.9 80290.2) (224997.9 80290.2) (224997.9 78140.2) (226197.9 78140.2)))
   ("T" "CLD-P4-KOL-YAZI" 225047.9 78540.2 20.0 0 "jenerat\\U+00F6r yedek (ATS \\U+00F6ncesi)")
   ("T" "CLD-P4-KOL-YAZI" 225047.9 78490.2 20.0 0 "NHXH-FE180/E90 5x10 mm\\U+00B2")
   ("L" "CLD-P4-KOL-SEMA" 230847.9 80290.2 230847.9 80390.2)
   ("P" "CLD-P4-KOL-SEMA" nil 10.0 ((230847.9 80390.2) (242647.9 80390.2)))
   ("T" "CLD-P4-KOL-YAZI" 230897.9 80310.2 25.0 0 "\\U+015EEBEKE BARASI")
   ("P" "CLD-P4-KOL-SEMA" nil 4.0 ((231247.9 79240.2) (243522.9 79240.2) (243522.9 80590.2)))
   ("P" "CLD-P4-KOL-SEMA" nil 10.0 ((243522.9 80590.2) (246747.9 80590.2)))
   ("T" "CLD-P4-KOL-YAZI" 243572.9 80630.2 25.0 0 "AC\\U+0130L BARA (ATS - jenerat\\U+00F6r destekli)")
   ("T" "CLD-P4-KOL-YAZI" 231297.9 79280.2 20.0 0 "ATS \\U+00E7\\U+0131k\\U+0131\\U+015F\\U+0131")
   ("L" "CLD-P4-KOL-SEMA" 232247.9 80390.2 232247.9 81340.2)
   ("P" "CLD-P4-KOL-SEMA" T 4.0 ((231376.6 81340.2) (233119.1 81340.2) (233119.1 82440.2) (231376.6 82440.2)))
   ("T" "CLD-P4-KOL-YAZI" 232247.9 82370.2 32.0 1 "MKP")
   ("T" "CLD-P4-KOL-YAZI" 232247.9 82320.2 25.0 1 "MEKAN\\U+0130K PANOSU")
   ("T" "CLD-P4-KOL-YAZI" 232247.9 82270.2 25.0 1 "Kurulu 36,35 kW")
   ("T" "CLD-P4-KOL-YAZI" 232247.9 82220.2 25.0 1 "Giri\\U+015F 63 A + 300 mA S")
   ("T" "CLD-P4-KOL-YAZI" 232287.9 80865.2 20.0 0 "NYY 3x25+16 + 1x16 (PE) mm\\U+00B2")
   ("T" "CLD-P4-KOL-YAZI" 232287.9 80825.2 20.0 0 "L=6,5 m %e=0,08")
   ("L" "CLD-P4-KOL-SEMA" 234297.9 80390.2 234297.9 81340.2)
   ("P" "CLD-P4-KOL-SEMA" T 4.0 ((233426.6 81340.2) (235169.1 81340.2) (235169.1 82440.2) (233426.6 82440.2)))
   ("T" "CLD-P4-KOL-YAZI" 234297.9 82370.2 32.0 1 "UTP-1")
   ("T" "CLD-P4-KOL-YAZI" 234297.9 82320.2 25.0 1 "\\U+00DCRET\\U+0130M TAL\\U+0130 PANOSU 1")
   ("T" "CLD-P4-KOL-YAZI" 234297.9 82270.2 25.0 1 "Kurulu 57,86 kW")
   ("T" "CLD-P4-KOL-YAZI" 234297.9 82220.2 25.0 1 "Giri\\U+015F 80 A + 300 mA S")
   ("T" "CLD-P4-KOL-YAZI" 234297.9 82170.2 25.0 1 "21 linye")
   ("T" "CLD-P4-KOL-YAZI" 234337.9 80865.2 20.0 0 "NYY 3x35+25 + 1x16 (PE) mm\\U+00B2")
   ("T" "CLD-P4-KOL-YAZI" 234337.9 80825.2 20.0 0 "L=75,0 m %e=0,88")
   ("L" "CLD-P4-KOL-SEMA" 236347.9 80390.2 236347.9 81340.2)
   ("P" "CLD-P4-KOL-SEMA" T 4.0 ((235476.6 81340.2) (237219.1 81340.2) (237219.1 82440.2) (235476.6 82440.2)))
   ("T" "CLD-P4-KOL-YAZI" 236347.9 82370.2 32.0 1 "UTP-2")
   ("T" "CLD-P4-KOL-YAZI" 236347.9 82320.2 25.0 1 "\\U+00DCRET\\U+0130M TAL\\U+0130 PANOSU 2")
   ("T" "CLD-P4-KOL-YAZI" 236347.9 82270.2 25.0 1 "Kurulu 52,26 kW")
   ("T" "CLD-P4-KOL-YAZI" 236347.9 82220.2 25.0 1 "Giri\\U+015F 80 A + 300 mA S")
   ("T" "CLD-P4-KOL-YAZI" 236347.9 82170.2 25.0 1 "21 linye")
   ("T" "CLD-P4-KOL-YAZI" 236387.9 80865.2 20.0 0 "NYY 3x35+25 + 1x16 (PE) mm\\U+00B2")
   ("T" "CLD-P4-KOL-YAZI" 236387.9 80825.2 20.0 0 "L=32,1 m %e=0,34")
   ("L" "CLD-P4-KOL-SEMA" 238397.9 80390.2 238397.9 81340.2)
   ("P" "CLD-P4-KOL-SEMA" T 4.0 ((237526.6 81340.2) (239269.1 81340.2) (239269.1 82440.2) (237526.6 82440.2)))
   ("T" "CLD-P4-KOL-YAZI" 238397.9 82370.2 32.0 1 "BARA-1")
   ("T" "CLD-P4-KOL-YAZI" 238397.9 82320.2 25.0 1 "250 A bara kanal\\U+0131")
   ("T" "CLD-P4-KOL-YAZI" 238397.9 82270.2 25.0 1 "P=89,34 kW")
   ("T" "CLD-P4-KOL-YAZI" 238397.9 82220.2 25.0 1 "250 A + 1 A S (ayarl\\U+0131 toroid)")
   ("T" "CLD-P4-KOL-YAZI" 238397.9 82170.2 25.0 1 "L=106,1 m %e=0,26")
   ("T" "CLD-P4-KOL-YAZI" 238437.9 80865.2 20.0 0 "NYY 3x240+120 + 1x120 (PE) mm\\U+00B2")
   ("T" "CLD-P4-KOL-YAZI" 238437.9 80825.2 20.0 0 "L=106,1 m %e=0,26")
   ("L" "CLD-P4-KOL-SEMA" 240447.9 80390.2 240447.9 81340.2)
   ("P" "CLD-P4-KOL-SEMA" T 4.0 ((239576.6 81340.2) (241319.1 81340.2) (241319.1 82440.2) (239576.6 82440.2)))
   ("T" "CLD-P4-KOL-YAZI" 240447.9 82370.2 32.0 1 "BARA-2")
   ("T" "CLD-P4-KOL-YAZI" 240447.9 82320.2 25.0 1 "250 A bara kanal\\U+0131")
   ("T" "CLD-P4-KOL-YAZI" 240447.9 82270.2 25.0 1 "P=79,99 kW")
   ("T" "CLD-P4-KOL-YAZI" 240447.9 82220.2 25.0 1 "250 A + 1 A S (ayarl\\U+0131 toroid)")
   ("T" "CLD-P4-KOL-YAZI" 240447.9 82170.2 25.0 1 "L=83,9 m %e=0,19")
   ("T" "CLD-P4-KOL-YAZI" 240487.9 80865.2 20.0 0 "NYY 3x240+120 + 1x120 (PE) mm\\U+00B2")
   ("T" "CLD-P4-KOL-YAZI" 240487.9 80825.2 20.0 0 "L=83,9 m %e=0,19")
   ("L" "CLD-P4-KOL-SEMA" 242497.9 80390.2 242497.9 81340.2)
   ("P" "CLD-P4-KOL-SEMA" T 4.0 ((241626.6 81340.2) (243369.1 81340.2) (243369.1 82440.2) (241626.6 82440.2)))
   ("T" "CLD-P4-KOL-YAZI" 242497.9 82370.2 32.0 1 "CEPHE AYD.")
   ("T" "CLD-P4-KOL-YAZI" 242497.9 82320.2 25.0 1 "14 x projekt\\U+00F6r")
   ("T" "CLD-P4-KOL-YAZI" 242497.9 82270.2 25.0 1 "P=1,40 kW")
   ("T" "CLD-P4-KOL-YAZI" 242497.9 82220.2 25.0 1 "16 A + fotosel")
   ("T" "CLD-P4-KOL-YAZI" 242497.9 82170.2 25.0 1 "L=127,5 m %e=0,80")
   ("T" "CLD-P4-KOL-YAZI" 242537.9 80865.2 20.0 0 "NYY 5x2,5 mm\\U+00B2")
   ("T" "CLD-P4-KOL-YAZI" 242537.9 80825.2 20.0 0 "L=127,5 m %e=0,80")
   ("L" "CLD-P4-KOL-SEMA" 244547.9 80590.2 244547.9 81340.2)
   ("P" "CLD-P4-KOL-SEMA" T 4.0 ((243676.6 81340.2) (245419.1 81340.2) (245419.1 82440.2) (243676.6 82440.2)))
   ("T" "CLD-P4-KOL-YAZI" 244547.9 82370.2 32.0 1 "IDP-ZK")
   ("T" "CLD-P4-KOL-YAZI" 244547.9 82320.2 25.0 1 "\\U+0130DAR\\U+0130 B\\U+00D6L\\U+00DCM ZEM\\U+0130N KAT PANO")
   ("T" "CLD-P4-KOL-YAZI" 244547.9 82270.2 25.0 1 "Kurulu 36,55 kW")
   ("T" "CLD-P4-KOL-YAZI" 244547.9 82220.2 25.0 1 "Giri\\U+015F 63 A + 300 mA S")
   ("T" "CLD-P4-KOL-YAZI" 244547.9 82170.2 25.0 1 "34 linye")
   ("T" "CLD-P4-KOL-YAZI" 244587.9 80965.2 20.0 0 "NYY 3x25+16 + 1x16 (PE) mm\\U+00B2")
   ("T" "CLD-P4-KOL-YAZI" 244587.9 80925.2 20.0 0 "L=41,7 m %e=0,54")
   ("L" "CLD-P4-KOL-SEMA" 246597.9 80590.2 246597.9 83390.2)
   ("P" "CLD-P4-KOL-SEMA" T 4.0 ((245726.6 83390.2) (247469.1 83390.2) (247469.1 84490.2) (245726.6 84490.2)))
   ("T" "CLD-P4-KOL-YAZI" 246597.9 84420.2 32.0 1 "IDP-1K")
   ("T" "CLD-P4-KOL-YAZI" 246597.9 84370.2 25.0 1 "\\U+0130DAR\\U+0130 B\\U+00D6L\\U+00DCM 1. KAT PANOSU")
   ("T" "CLD-P4-KOL-YAZI" 246597.9 84320.2 25.0 1 "Kurulu 27,70 kW")
   ("T" "CLD-P4-KOL-YAZI" 246597.9 84270.2 25.0 1 "Giri\\U+015F 50 A + 300 mA S")
   ("T" "CLD-P4-KOL-YAZI" 246597.9 84220.2 25.0 1 "25 linye")
   ("T" "CLD-P4-KOL-YAZI" 246637.9 81990.2 20.0 0 "NYY 5x16 mm\\U+00B2")
   ("T" "CLD-P4-KOL-YAZI" 246637.9 81950.2 20.0 0 "L=50,1 m %e=0,77")))))
(defun cld:ops-p4_kolon_semasi-2 () (cld:play (quote (
   ("T" "CLD-P4-KOL-YAZI" 224297.9 77340.2 30.0 0 "Topraklama: ADP PE baras\\U+0131 \\U+2192 AEB \\U+2192 temel topraklama a\\U+011F\\U+0131 (birle\\U+015Fik topraklama, R \\U+2264 2 \\U+03A9)")
   ("T" "CLD-P4-KOL-YAZI" 224297.9 77260.2 25.0 0 "Kablolar Cu, IEC 60364-5-52 C y\\U+00F6ntemi x d\\U+00FCzeltme katsay\\U+0131lar\\U+0131, gerilim d\\U+00FC\\U+015F\\U+00FCm\\U+00FC \\U+2264 %1,5. De\\U+011Ferler y\\U+00FCkleme cetvelleri ile uyumludur.")
   ("P" "CLD-P4-KOL-PAFTA" T 10.0 ((224047.9 76090.2) (250747.9 76090.2) (250747.9 85940.2) (224047.9 85940.2)))
   ("P" "CLD-P4-KOL-PAFTA" nil 6.0 ((224047.9 76840.2) (250747.9 76840.2)))
   ("T" "CLD-P4-KOL-YAZI" 224147.9 76650.2 70.0 0 "HESAP TABLOLARI, CETVELLER VE NOTLAR")
   ("T" "CLD-P4-KOL-YAZI" 224147.9 76490.2 40.0 0 "KOLON \\U+015EEMASI (TEK HAT DA\\U+011EITIM \\U+015EEMASI)  -  \\U+00D6l\\U+00E7eksiz")
   ("P" "CLD-P4-KOL-PAFTA" T 6.0 ((248247.9 76110.2) (250747.9 76110.2) (250747.9 76820.2) (248247.9 76820.2)))
   ("T" "CLD-P4-KOL-YAZI" 248277.9 76754.3 18.0 0 "\\U+0130\\U+015E\\U+0130N ADI")
   ("T" "CLD-P4-KOL-YAZI" 248867.9 76754.3 20.0 0 "KOLON \\U+015EEMASI (TEK HAT DA\\U+011EITIM \\U+015EEMASI)")
   ("L" "CLD-P4-KOL-PAFTA" 248247.9 76718.8 250747.9 76718.8)
   ("T" "CLD-P4-KOL-YAZI" 248277.9 76652.9 18.0 0 "YAPI SAH\\U+0130B\\U+0130")
   ("T" "CLD-P4-KOL-YAZI" 248867.9 76652.9 20.0 0 "BROSCO \\U+0130THALAT \\U+0130HRACAT VE T\\U+0130CARET ANON\\U+0130M \\U+015E\\U+0130RKET\\U+0130")
   ("L" "CLD-P4-KOL-PAFTA" 248247.9 76617.4 250747.9 76617.4)
   ("T" "CLD-P4-KOL-YAZI" 248277.9 76551.5 18.0 0 "ADRES")
   ("T" "CLD-P4-KOL-YAZI" 248867.9 76551.5 20.0 0 "ULUCAK / KEMALPA\\U+015EA / \\U+0130ZM\\U+0130R  -  Ada: ......  Parsel: 4")
   ("L" "CLD-P4-KOL-PAFTA" 248247.9 76516.0 250747.9 76516.0)
   ("T" "CLD-P4-KOL-YAZI" 248277.9 76450.0 18.0 0 "PAFTA ADI")
   ("T" "CLD-P4-KOL-YAZI" 248867.9 76450.0 20.0 0 "HESAP TABLOLARI VE NOTLAR")
   ("L" "CLD-P4-KOL-PAFTA" 248247.9 76414.5 250747.9 76414.5)
   ("T" "CLD-P4-KOL-YAZI" 248277.9 76348.6 18.0 0 "\\U+00D6L\\U+00C7EK / TAR\\U+0130H / PAFTA NO")
   ("T" "CLD-P4-KOL-YAZI" 248867.9 76348.6 20.0 0 "\\U+00D6l\\U+00E7eksiz   |   19.10.2026   |   08-01")
   ("L" "CLD-P4-KOL-PAFTA" 248247.9 76313.1 250747.9 76313.1)
   ("T" "CLD-P4-KOL-YAZI" 248277.9 76247.2 18.0 0 "PROJE M\\U+00DCELL\\U+0130F\\U+0130")
   ("T" "CLD-P4-KOL-YAZI" 248867.9 76247.2 20.0 0 "Elektrik M\\U+00FChendisi - Ad\\U+0131 Soyad\\U+0131: ..............................")
   ("L" "CLD-P4-KOL-PAFTA" 248247.9 76211.7 250747.9 76211.7)
   ("T" "CLD-P4-KOL-YAZI" 248277.9 76145.7 18.0 0 "ODA S\\U+0130C\\U+0130L / SMM NO")
   ("T" "CLD-P4-KOL-YAZI" 248867.9 76145.7 20.0 0 "EMO Sicil No: ............   SMM Belge No: ............   \\U+0130mza: ............")
   ("L" "CLD-P4-KOL-PAFTA" 248837.9 76110.2 248837.9 76820.2)))))

(defun c:CLD_P4_KOLONSEMASI ( / *error* olderr)
  (setq *error* cld:err)
  (setq *cld-u* 100.0 *cld-ext* (list 0.0 0.0 1.0))
  (cld:begin "CLD-P4-KOL-*")
  (cld:unlock "CLD-P4-KOL-*")
  (cld:unlock "CLD-KOL-*")
  (cld:clear "CLD-KOL-*")
  (cld:ops-p4_kolon_semasi-layers)
  (cld:clear "CLD-P4-KOL-*")
  (cld:def-symbols)
  (cld:ops-p4_kolon_semasi-1)
  (cld:ops-p4_kolon_semasi-2)
  (cld:end "CLD: Parsel 4 - KOLON SEMASI (TEK HAT DAGITIM SEMASI) cizildi")
  (princ))

(if (cld:wrong-dwg "4" (list "2" "3" "5"))
  (princ "\nCLD UYARI: Bu dosya PARSEL 4 icindir; acik cizim baska bir parsele ait gorunuyor. Yine de cizmek icin CLD_P4_KOLONSEMASI yazin.")
  (progn (princ "\nCLD: Parsel 4 KOLON_SEMASI yukleniyor, cizim olusturuluyor...") (c:CLD_P4_KOLONSEMASI)))
(princ "\nCLD: Yeniden cizmek icin komut: CLD_P4_KOLONSEMASI")
(princ)
