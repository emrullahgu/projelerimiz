;;; ==========================================================================
;;; CLD CORE  -  ortak cizim altyapisi (katman, stil, varlik, tablo, oynatici)
;;; Tum isimler CLD onekli. ActiveX (vla-) kullanilmaz: AutoCAD / BricsCAD /
;;; accoreconsole uyumlu saf AutoLISP + entmake.
;;; Mimari paftalar WCS XZ duzleminde (ekstruzyon 0,-1,0) cizildiginden tum
;;; varliklar ayni duzlemde (*cld-ext*) uretilir; koordinatlar pafta (OCS)
;;; koordinatidir.
;;; ==========================================================================

(setq *cld-ver* "1.0")
(if (not *cld-ext*) (setq *cld-ext* '(0.0 0.0 1.0)))
(if (not *cld-u*) (setq *cld-u* 100.0))

;;; ---------------------------------------------------------------- yardimci
(defun cld:m (x) (* x *cld-u*))
(defun cld:3d (p) (list (float (car p)) (float (cadr p)) 0.0))
(defun cld:2d (p) (list (float (car p)) (float (cadr p))))
(defun cld:pxy (p dx dy) (list (+ (car p) dx) (+ (cadr p) dy)))
(defun cld:wcs (p) (trans (cld:3d p) *cld-ext* 0))
(defun cld:top (lay) (/= lay "0"))
(defun cld:x210 (lay) (if (cld:top lay) (list (cons 210 *cld-ext*) '(410 . "Model")) '()))
;; renk / cizgi tipi / kalinlik her zaman acik yazilir: cizimdeki CECOLOR / CELTYPE / CELWEIGHT ne olursa olsun
;; katmandan (ByLayer) gelir; blok icindekiler ByBlock
(defun cld:col (lay)
  (if (= lay "0") '((62 . 0) (6 . "ByBlock") (370 . -2)) '((62 . 256) (6 . "ByLayer") (370 . -1))))
(defun cld:dlen (s / n i)
  ;; gorunen karakter sayisi (\U+XXXX = 1 karakter)
  (setq n 0 i 1)
  (while (<= i (strlen s))
    (if (and (= (substr s i 3) "\\U+") (<= (+ i 6) (strlen s))) (setq i (+ i 7)) (setq i (1+ i)))
    (setq n (1+ n)))
  n)
(defun cld:maxl (l) (if l (apply 'max l) 0))
(defun cld:sum (l) (apply '+ (cons 0 l)))
(defun cld:nth-or (i l def) (if (and l (< i (length l))) (nth i l) def))
(defun cld:range (n / i r) (setq i (1- n)) (while (>= i 0) (setq r (cons i r) i (1- i))) r)

;;; ------------------------------------------------------ tablo kayitlari
(defun cld:ltype (nm desc dash gap / sc)
  (if (not (tblsearch "LTYPE" nm))
    (progn
      (setq sc (max 1e-6 (getvar "LTSCALE")))
      (entmake (list '(0 . "LTYPE") '(100 . "AcDbSymbolTableRecord") '(100 . "AcDbLinetypeTableRecord")
                     (cons 2 nm) '(70 . 0) (cons 3 desc) '(72 . 65) '(73 . 2)
                     (cons 40 (/ (+ dash gap) sc)) (cons 49 (/ dash sc)) '(74 . 0) (cons 49 (- (/ gap sc))) '(74 . 0)))))
  nm)
(defun cld:style ()
  (if (not (tblsearch "STYLE" "CLD_YAZI"))
    (entmake '((0 . "STYLE") (100 . "AcDbSymbolTableRecord") (100 . "AcDbTextStyleTableRecord")
               (2 . "CLD_YAZI") (70 . 0) (40 . 0.0) (41 . 0.85) (50 . 0.0) (71 . 0) (42 . 2.5)
               (3 . "arial.ttf") (4 . ""))))
  "CLD_YAZI")
(defun cld:lay (nm col lt lw / e ed)
  (if (not (tblsearch "LAYER" nm))
    (entmake (list '(0 . "LAYER") '(100 . "AcDbSymbolTableRecord") '(100 . "AcDbLayerTableRecord")
                   (cons 2 nm) '(70 . 0) (cons 62 col)
                   (cons 6 (if (and lt (tblsearch "LTYPE" lt)) lt "Continuous"))
                   (cons 370 lw)))
    (progn
      (setq e (tblobjname "LAYER" nm) ed (entget e))
      (setq ed (subst (cons 70 0) (assoc 70 ed) ed))
      (setq ed (subst (cons 62 col) (assoc 62 ed) ed))
      (if (and lt (tblsearch "LTYPE" lt) (assoc 6 ed)) (setq ed (subst (cons 6 lt) (assoc 6 ed) ed)))
      (if (assoc 370 ed) (setq ed (subst (cons 370 lw) (assoc 370 ed) ed)))
      (entmod ed)))
  nm)

;;; ---------------------------------------------------- varlik olusturucular
;;; lay "0" = blok tanimi icerigi (BYBLOCK renk, blok koordinati)
(defun cld:e-line (a b lay)
  (append (list '(0 . "LINE") (cons 8 lay)) (cld:col lay)
          (if (cld:top lay) (list (cons 10 (cld:wcs a)) (cons 11 (cld:wcs b))) (list (cons 10 (cld:3d a)) (cons 11 (cld:3d b))))
          (cld:x210 lay)))
(defun cld:e-circle (c r lay)
  (append (list '(0 . "CIRCLE") (cons 8 lay)) (cld:col lay) (list (cons 10 (cld:3d c)) (cons 40 r)) (cld:x210 lay)))
(defun cld:e-arc (c r a1 a2 lay)
  (append (list '(0 . "ARC") (cons 8 lay)) (cld:col lay) (list (cons 10 (cld:3d c)) (cons 40 r) (cons 50 a1) (cons 51 a2)) (cld:x210 lay)))
(defun cld:e-pl (pts closed w lay)
  (append (list '(0 . "LWPOLYLINE") '(100 . "AcDbEntity") (cons 8 lay)) (cld:col lay)
          (list '(100 . "AcDbPolyline") (cons 90 (length pts)) (cons 70 (+ (if closed 1 0) (if (cld:top lay) 128 0))) (cons 43 w) '(38 . 0.0))
          (mapcar '(lambda (p) (cons 10 (cld:2d p))) pts)
          (cld:x210 lay)))
(defun cld:e-dot (c r lay)
  (append (list '(0 . "LWPOLYLINE") '(100 . "AcDbEntity") (cons 8 lay)) (cld:col lay)
          (list '(100 . "AcDbPolyline") '(90 . 2) '(70 . 1) (cons 43 r) '(38 . 0.0)
                (cons 10 (list (- (car c) (/ r 2.0)) (cadr c))) '(42 . 1.0)
                (cons 10 (list (+ (car c) (/ r 2.0)) (cadr c))) '(42 . 1.0))
          (cld:x210 lay)))
(defun cld:e-solid (p1 p2 p3 p4 lay)
  (append (list '(0 . "SOLID") (cons 8 lay)) (cld:col lay)
          (list (cons 10 (cld:3d p1)) (cons 11 (cld:3d p2)) (cons 12 (cld:3d p4)) (cons 13 (cld:3d p3)))
          (cld:x210 lay)))
(defun cld:e-text (p h s j lay / ed p3)
  ;; j: 0 sol-taban, 1 orta-taban, 2 sag-taban, 4 orta-orta, 7 sol-orta, 9 sag-orta
  (setq p3 (cld:3d p))
  (setq ed (append (list '(0 . "TEXT") (cons 8 lay)) (cld:col lay)
                   (list (cons 7 (cld:style)) (cons 10 p3) (cons 40 h) (cons 1 s) '(50 . 0.0) '(41 . 0.85))))
  (setq ed (cond ((= j 1) (append ed (list '(72 . 1) (cons 11 p3) '(73 . 0))))
                 ((= j 2) (append ed (list '(72 . 2) (cons 11 p3) '(73 . 0))))
                 ((= j 4) (append ed (list '(72 . 1) (cons 11 p3) '(73 . 2))))
                 ((= j 7) (append ed (list '(72 . 0) (cons 11 p3) '(73 . 2))))
                 ((= j 9) (append ed (list '(72 . 2) (cons 11 p3) '(73 . 2))))
                 (T ed)))
  (append ed (cld:x210 lay)))
(defun cld:e-ins (blk p sc rot lay)
  (append (list '(0 . "INSERT") (cons 8 lay)) (cld:col lay) (list (cons 2 blk) (cons 10 (cld:3d p))
                (cons 41 sc) (cons 42 sc) (cons 43 sc) (cons 50 rot))
          (cld:x210 lay)))
(defun cld:line (a b lay) (entmake (cld:e-line a b lay)))
(defun cld:pl (pts closed w lay) (if (cdr pts) (entmake (cld:e-pl pts closed w lay))))
(defun cld:txt (p h s j lay) (entmake (cld:e-text p h s j lay)))
(defun cld:rect (p1 p2 lay) (cld:pl (list p1 (list (car p2) (cadr p1)) p2 (list (car p1) (cadr p2))) T 0.0 lay))

;;; ------------------------------------------------------------ blok tanimi
(defun cld:defblk (name ents)
  (if (not (tblsearch "BLOCK" name))
    (progn
      (entmake (list '(0 . "BLOCK") (cons 2 name) '(70 . 0) '(10 0.0 0.0 0.0) '(8 . "0")))
      (foreach e ents (entmake e))
      (entmake '((0 . "ENDBLK") (8 . "0")))))
  name)

;;; mimari altlik blogu: plines ((kapali (x y) (x y) ...) ...)  texts ((x y h "yazi") ...)
(defun cld:defblk-bg (name plines texts)
  (if (not (tblsearch "BLOCK" name))
    (progn
      (entmake (list '(0 . "BLOCK") (cons 2 name) '(70 . 0) '(10 0.0 0.0 0.0) '(8 . "0")))
      (foreach p plines (if (cddr p) (entmake (cld:e-pl (cdr p) (car p) 0.0 "0"))))
      (foreach s texts (entmake (cld:e-text (list (car s) (cadr s)) (caddr s) (cadddr s) 4 "0")))
      (entmake '((0 . "ENDBLK") (8 . "0")))))
  name)

;;; ------------------------------------------------------------------ tablo
;;; rows: ((hucre ...) ...)  ilk satir baslik. Sutun genislikleri otomatik.
(defun cld:table (org title rows h lay / ncol widths rh y x w i r cw tw pad s)
  (setq pad (* 0.6 h) rh (* 2.0 h))
  (setq ncol (cld:maxl (mapcar 'length rows)))
  (setq widths (mapcar '(lambda (c)
                          (+ (* 2 pad) (* 0.66 h (cld:maxl (mapcar '(lambda (r) (cld:dlen (cld:nth-or c r ""))) rows)))))
                       (cld:range ncol)))
  (setq tw (cld:sum widths) x (car org) y (cadr org))
  (if (and title (/= title ""))
    (progn
      (cld:rect (list x y) (list (+ x tw) (- y (* 1.5 rh))) lay)
      (cld:txt (list (+ x pad) (- y (* 0.75 rh))) (* 1.3 h) title 7 lay)
      (setq y (- y (* 1.5 rh)))))
  (setq i 0)
  (foreach r rows
    (setq x (car org) cw 0)
    (cld:rect (list x y) (list (+ x tw) (- y rh)) lay)
    (foreach w widths
      (if (> cw 0) (cld:line (list x y) (list x (- y rh)) lay))
      (setq s (cld:nth-or cw r ""))
      (if (/= s "") (cld:txt (list (+ x pad) (- y (* 0.5 rh))) h s 7 lay))
      (setq x (+ x w) cw (1+ cw)))
    (if (= i 0) (cld:pl (list (list (car org) (- y rh)) (list (+ (car org) tw) (- y rh))) nil (* 0.12 h) lay))
    (setq y (- y rh) i (1+ i)))
  (list (- y (* 2.0 h)) tw))
(defun cld:notes (org title lines h lay / y)
  (setq y (cadr org))
  (if (and title (/= title "")) (progn (cld:txt (list (car org) y) (* 1.3 h) title 0 lay) (setq y (- y (* 2.2 h)))))
  (foreach s lines (cld:txt (list (car org) y) h s 0 lay) (setq y (- y (* 1.7 h))))
  (- y h))

;;; ------------------------------------------------------------- oynatici
;;; Hesap motorunun urettigi cizim komutlari:
;;;  ("LY" ad renk cizgitipi kalinlik)        katman
;;;  ("I" lay blok x y aci olcek)             sembol (olcek * *cld-u*)
;;;  ("L" lay x1 y1 x2 y2)                    cizgi
;;;  ("P" lay kapali genislik ((x y) ...))    polyline
;;;  ("C" lay x y r)                          daire
;;;  ("D" lay x y r)                          dolu daire
;;;  ("T" lay x y h hiza "yazi")              yazi
;;;  ("TB" lay x y h "baslik" satirlar)       tablo
;;;  ("NT" lay x y h "baslik" satirlar)       not blogu
(defun cld:op (o / k)
  (setq k (car o))
  (cond ((= k "I") (entmake (cld:e-ins (nth 2 o) (list (nth 3 o) (nth 4 o)) (* (nth 6 o) *cld-u*) (nth 5 o) (nth 1 o))))
        ((= k "L") (cld:line (list (nth 2 o) (nth 3 o)) (list (nth 4 o) (nth 5 o)) (nth 1 o)))
        ((= k "P") (cld:pl (nth 4 o) (nth 2 o) (nth 3 o) (nth 1 o)))
        ((= k "C") (entmake (cld:e-circle (list (nth 2 o) (nth 3 o)) (nth 4 o) (nth 1 o))))
        ((= k "D") (entmake (cld:e-dot (list (nth 2 o) (nth 3 o)) (nth 4 o) (nth 1 o))))
        ((= k "T") (cld:txt (list (nth 2 o) (nth 3 o)) (nth 4 o) (nth 6 o) (nth 5 o) (nth 1 o)))
        ((= k "TB") (cld:table (list (nth 2 o) (nth 3 o)) (nth 5 o) (nth 6 o) (nth 4 o) (nth 1 o)))
        ((= k "NT") (cld:notes (list (nth 2 o) (nth 3 o)) (nth 5 o) (nth 6 o) (nth 4 o) (nth 1 o)))
        ((= k "LY") (cld:lay (nth 1 o) (nth 2 o) (nth 3 o) (nth 4 o)))
        ((= k "BK") (cld:defblk-bg (nth 1 o) (nth 2 o) (nth 3 o)))))
(defun cld:play (ops / r)
  (foreach o ops
    (setq r (vl-catch-all-apply 'cld:op (list o)))
    (cond ((vl-catch-all-error-p r) (setq *cld-bad* (cons (list (car o) (nth 1 o) (vl-catch-all-error-message r)) *cld-bad*)))
          ((and (null r) (or (member (car o) '("I" "L" "C" "D" "T")) (and (= (car o) "P") (cdr (nth 4 o)))))
           (setq *cld-bad* (cons (list (car o) (nth 1 o) (if (= (car o) "I") (nth 2 o) "")) *cld-bad*)))
          (T (setq *cld-n* (1+ *cld-n*))))))

;;; ------------------------------------------------------- calisma ortami
(defun cld:clear (pat / ss i n)
  (setq n 0)
  (if (setq ss (ssget "_X" (list (cons 8 pat))))
    (progn (setq i 0) (while (< i (sslength ss)) (entdel (ssname ss i)) (setq i (1+ i) n (1+ n)))))
  n)
(defun cld:begin (pat)
  (setq *cld-old* (list (getvar "CMDECHO") (getvar "OSMODE")) *cld-n* 0 *cld-bad* nil)
  (setvar "CMDECHO" 0)
  (setvar "OSMODE" 0)
  ;; cizim model alaninda olusur (bir yerlesim sekmesi acik olsa bile)
  (if (= 0 (getvar "TILEMODE")) (vl-catch-all-apply 'setvar (list "TILEMODE" 1)))
  (vl-catch-all-apply 'command-s (list "_.UNDO" "_BEGIN"))
  (cld:style)
  (cld:ltype "CLD_KESIK" "CLD kesik __ __" (cld:m 0.30) (cld:m 0.15))
  (cld:ltype "CLD_NOKTALI" "CLD noktali . . ." (cld:m 0.05) (cld:m 0.10))
  (cld:ltype "CLD_UZUNKESIK" "CLD uzun kesik ____ ____" (cld:m 0.80) (cld:m 0.20)))
;;; disiplin katmanlarinin kilidini kaldir / coz (eski cikti silinebilsin)
(defun cld:unlock (pat / tl ed)
  (setq tl (tblnext "LAYER" T))
  (while tl
    (if (and (wcmatch (cdr (assoc 2 tl)) pat) (/= 0 (logand 5 (cdr (assoc 70 tl)))))
      (progn (setq ed (entget (tblobjname "LAYER" (cdr (assoc 2 tl)))))
             (entmod (subst (cons 70 0) (assoc 70 ed) ed))))
    (setq tl (tblnext "LAYER"))))
(defun cld:restore ()
  (vl-catch-all-apply 'command-s (list "_.UNDO" "_END"))
  (if *cld-old* (progn (setvar "CMDECHO" (car *cld-old*)) (setvar "OSMODE" (cadr *cld-old*))))
  (setq *cld-old* nil))
(defun cld:first5 (l / r i) (setq i 0) (foreach x l (if (< i 5) (setq r (cons x r))) (setq i (1+ i))) (reverse r))
(defun cld:end (msg)
  (cld:restore)
  (princ (strcat "\n" msg " (" (itoa *cld-n*) " varlik/komut)"))
  (if *cld-bad*
    (progn
      (princ (strcat "\nCLD UYARI: " (itoa (length *cld-bad*)) " varlik olusturulamadi, ilkleri:"))
      (foreach b (cld:first5 (reverse *cld-bad*)) (princ (strcat "\n   " (vl-princ-to-string b))))))
  (princ))
;;; acik cizim baska bir parsele mi ait? (dosya adinda baska parselin "<n> NOLU" ifadesi)
(defun cld:wrong-dwg (parcel others / nm bad)
  (setq nm (strcase (getvar "DWGNAME")))
  (foreach o others (if (wcmatch nm (strcat "* " o " NOLU*,BROSCO " o " *,P" o ".DWG")) (setq bad T)))
  (and bad (not (wcmatch nm (strcat "* " parcel " NOLU*,BROSCO " parcel " *,P" parcel ".DWG")))))
(defun cld:err (m)
  (cld:restore)
  (if (not (member m '("Function cancelled" "quit / exit abort"))) (princ (strcat "\nCLD HATA: " m)))
  (princ))
