;;; CLDX dump v4 - drawing data extractor (analysis only).
;;; All model coordinates are written in the PLAN plane coordinate system: the OCS of
;;; the dominant 2D drawing extrusion (*cldx-pe*). Entities in other planes (3D model) skipped.
(defun cldx:s (x) (if (= (type x) 'STR) x (vl-princ-to-string x)))
(defun cldx:r (x) (rtos x 2 2))
(defun cldx:clean (s) (vl-string-translate "\t\r\n" "   " s))
(defun cldx:inc (key alist / a)
  (if (setq a (assoc key alist)) (subst (cons key (1+ (cdr a))) a alist) (cons (cons key 1) alist)))
(defun cldx:mtext (ed / s)
  (setq s "")
  (foreach p ed (if (= (car p) 3) (setq s (strcat s (cdr p)))))
  (strcat s (cdr (assoc 1 ed))))
(defun cldx:veq (a b) (and a b (equal a b 1e-3)))
(defun cldx:ext (ed) (cond ((cdr (assoc 210 ed))) (T '(0.0 0.0 1.0))))
(defun cldx:pp (p) (strcat (cldx:r (car p)) "," (cldx:r (cadr p))))
;; WCS point -> plan (x y elev)
(defun cldx:wp (p) (trans p 0 *cldx-pe*))
;; entity OCS point -> plan
(defun cldx:op (p e ed)
  (if (cldx:veq (cldx:ext ed) *cldx-pe*) p (trans (trans p e 0) 0 *cldx-pe*)))
;; block-internal OCS point -> block XY
(defun cldx:bp (p e ed / q)
  (if (cldx:veq (cldx:ext ed) '(0.0 0.0 1.0)) p (if (setq q (trans p (cldx:ext ed) 0)) q p)))
(defun cldx:pt (p e ed inblk) (if inblk (cldx:bp p e ed) (cldx:op p e ed)))
(defun cldx:okz (p) (< (abs (caddr p)) 1000.0))
(setq *cldx-bb* nil)
(defun cldx:bb-add (p)
  (if (and p (numberp (car p)) (numberp (cadr p)))
  (if *cldx-bb*
    (setq *cldx-bb* (list (min (car *cldx-bb*) (car p)) (min (cadr *cldx-bb*) (cadr p)) (max (caddr *cldx-bb*) (car p)) (max (cadddr *cldx-bb*) (cadr p))))
    (setq *cldx-bb* (list (car p) (cadr p) (car p) (cadr p))))))

(defun cldx:ent (f ed owner inblk / e typ lay pt p11 e2 ed2 s q c r a1 a2 n i p maj rat t0 t1 v ve z ok mir)
  (setq e (cdr (assoc -1 ed)) typ (cdr (assoc 0 ed)) lay (cdr (assoc 8 ed)))
  ;; plane filter for model space (LINE/MTEXT/ELLIPSE/SPLINE are WCS-based)
  (setq mir (and (not inblk) (cldx:veq (cldx:ext ed) (mapcar '- *cldx-pe*))))
  (setq ok (or inblk mir (member typ '("LINE" "MTEXT" "ELLIPSE" "SPLINE")) (cldx:veq (cldx:ext ed) *cldx-pe*)))
  (if ok
  (cond
    ((= typ "TEXT")
     (setq pt (cldx:pt (cdr (assoc 10 ed)) e ed inblk) p11 (cldx:pt (cdr (assoc 11 ed)) e ed inblk))
     (if (or inblk (cldx:okz pt))
       (write-line (strcat "TXT\t" owner "\t" lay "\t" (cldx:r (car pt)) "\t" (cldx:r (cadr pt)) "\t" (cldx:r (cdr (assoc 40 ed))) "\t" (cldx:clean (cdr (assoc 1 ed)))
                           "\t" (cldx:r (car p11)) "\t" (cldx:r (cadr p11)) "\t" (itoa (cdr (assoc 72 ed))) "\t" (itoa (cdr (assoc 73 ed))) "\t" (rtos (cdr (assoc 50 ed)) 2 4)) f)))
    ((= typ "MTEXT")
     (setq pt (if inblk (cdr (assoc 10 ed)) (cldx:wp (cdr (assoc 10 ed)))))
     (if (or inblk (cldx:okz pt))
       (write-line (strcat "MTX\t" owner "\t" lay "\t" (cldx:r (car pt)) "\t" (cldx:r (cadr pt)) "\t" (cldx:r (cdr (assoc 40 ed))) "\t" (cldx:clean (cldx:mtext ed))
                           "\t" (cldx:r (car pt)) "\t" (cldx:r (cadr pt)) "\t" (itoa (cdr (assoc 71 ed))) "\t0\t0") f)))
    ((= typ "INSERT")
     (setq pt (cldx:pt (cdr (assoc 10 ed)) e ed inblk))
     (if (or inblk (cldx:okz pt))
       (progn
         (write-line (strcat "INS\t" owner "\t" lay "\t" (cldx:r (car pt)) "\t" (cldx:r (cadr pt)) "\t" (cdr (assoc 2 ed)) "\t" (rtos (* (if mir -1 1) (cdr (assoc 41 ed))) 2 4) "\t" (rtos (* (if mir -1 1) (cdr (assoc 50 ed))) 2 5)
                             "\t" (rtos (cdr (assoc 42 ed)) 2 4) "\t" (if (and inblk (not (cldx:veq (cldx:ext ed) '(0.0 0.0 1.0)))) "-1" "1") "\t" (cldx:s (cdr (assoc 5 ed)))) f)
         (if (= (cdr (assoc 66 ed)) 1)
           (progn
             (setq e2 (entnext e))
             (while (and e2 (setq ed2 (entget e2)) (= (cdr (assoc 0 ed2)) "ATTRIB"))
               (write-line (strcat "ATT\t" owner "\t" (cdr (assoc 2 ed2)) "\t" (cldx:clean (cdr (assoc 1 ed2))) "\t" (cldx:s (cdr (assoc 5 ed)))) f)
               (setq e2 (entnext e2))))))))
    ((= typ "LINE")
     (setq p (cdr (assoc 10 ed)) q (cdr (assoc 11 ed)))
     (if (not inblk) (setq p (cldx:wp p) q (cldx:wp q)))
     (if (or inblk (and (cldx:okz p) (cldx:okz q) (< (abs (- (caddr p) (caddr q))) 1.0)))
       (progn (if inblk (progn (cldx:bb-add p) (cldx:bb-add q)))
              (write-line (strcat "GL\t" owner "\t" lay "\t" (cldx:pp p) ";" (cldx:pp q)) f))))
    ((= typ "LWPOLYLINE")
     (setq s "" z (cond ((cdr (assoc 38 ed))) (T 0.0)))
     (if (or inblk (< (abs z) 1000.0))
       (progn
         (foreach p ed
           (cond ((= (car p) 10) (setq q (cldx:pt (list (cadr p) (caddr p) z) e ed inblk) s (strcat s ";" (cldx:pp q)))
                  (if inblk (cldx:bb-add q)))
                 ((= (car p) 42) (if (/= (cdr p) 0.0) (setq s (strcat s "," (rtos (cdr p) 2 4)))))))
         (write-line (strcat "GP\t" owner "\t" lay "\t" (itoa (logand 1 (cdr (assoc 70 ed)))) "\t" (substr s 2) "\t"
                             (if (and inblk (< (caddr (cldx:ext ed)) 0)) "-1" "1")) f))))
    ((member typ '("ARC" "CIRCLE"))
     (setq c (cdr (assoc 10 ed)) r (cdr (assoc 40 ed)))
     (if (or inblk (< (abs (caddr c)) 1000.0))
       (progn
         (if (= typ "CIRCLE") (setq a1 0.0 a2 (* 2 pi)) (setq a1 (cdr (assoc 50 ed)) a2 (cdr (assoc 51 ed))))
         (if (< a2 a1) (setq a2 (+ a2 (* 2 pi))))
         (setq n (max 2 (fix (/ (- a2 a1) 0.26))) i 0 s "")
         (while (<= i n)
           (setq p (list (+ (car c) (* r (cos (+ a1 (* i (/ (- a2 a1) n)))))) (+ (cadr c) (* r (sin (+ a1 (* i (/ (- a2 a1) n)))))) (caddr c)))
           (setq q (cldx:pt p e ed inblk))
           (if inblk (cldx:bb-add q))
           (setq s (strcat s ";" (cldx:pp q)) i (1+ i)))
         (write-line (strcat (if (= typ "ARC") "GA\t" "GC\t") owner "\t" lay "\t" (substr s 2)) f))))
    ((= typ "ELLIPSE")
     (setq c (cdr (assoc 10 ed)) maj (cdr (assoc 11 ed)) rat (cdr (assoc 40 ed)) t0 (cdr (assoc 41 ed)) t1 (cdr (assoc 42 ed)))
     (if (< t1 t0) (setq t1 (+ t1 (* 2 pi))))
     (setq n 16 i 0 s "")
     (setq v (cldx:ext ed))
     ;; minor axis = N x major * ratio
     (setq ve (list (- (* (cadr v) (caddr maj)) (* (caddr v) (cadr maj))) (- (* (caddr v) (car maj)) (* (car v) (caddr maj))) (- (* (car v) (cadr maj)) (* (cadr v) (car maj)))))
     (while (<= i n)
       (setq a1 (+ t0 (* i (/ (- t1 t0) n))))
       (setq p (mapcar '(lambda (cc mm nn) (+ cc (* mm (cos a1)) (* nn rat (sin a1)))) c maj ve))
       (setq q (if inblk p (cldx:wp p)))
       (setq s (strcat s ";" (cldx:pp q)) i (1+ i)))
     (if (or inblk (cldx:okz q)) (write-line (strcat "GE\t" owner "\t" lay "\t" (substr s 2)) f)))
    ((= typ "SPLINE")
     (setq s "")
     (foreach p ed (if (= (car p) (if (assoc 11 ed) 11 10)) (setq q (if inblk (cdr p) (cldx:wp (cdr p))) s (strcat s ";" (cldx:pp q)))))
     (if (and q (or inblk (cldx:okz q))) (write-line (strcat "GS\t" owner "\t" lay "\t" (substr s 2)) f)))
    ((= typ "POLYLINE")
     (if (= 0 (logand (+ 8 16 64) (cdr (assoc 70 ed))))
       (progn
         (setq s "" v (entnext e))
         (while (and v (= (cdr (assoc 0 (setq ve (entget v)))) "VERTEX"))
           (setq q (cldx:pt (cdr (assoc 10 ve)) e ed inblk) s (strcat s ";" (cldx:pp q)) v (entnext v)))
         (write-line (strcat "GP\t" owner "\t" lay "\t" (itoa (logand 1 (cdr (assoc 70 ed)))) "\t" (substr s 2) "\t1") f))))
  )))

(defun cldx:safe (f ed owner inblk / r)
  (setq r (vl-catch-all-apply 'cldx:ent (list f ed owner inblk)))
  (if (vl-catch-all-error-p r)
    (write-line (strcat "ERR	" owner "	" (cdr (assoc 0 ed)) "	" (vl-catch-all-error-message r) "	" (vl-princ-to-string (vl-remove-if '(lambda (p) (member (car p) '(-1 330 5 100 102 360))) ed))) f)))
(defun cldx:dump (fn / f tl ss i e ed cnt typ lay blk be bed bname bcnt space ext best)
  (setq f (open fn "w"))
  ;; dominant 2D plane from TEXT extrusions
  (setq cnt nil)
  (if (setq ss (ssget "_X" '((0 . "TEXT,INSERT,LWPOLYLINE") (410 . "Model"))))
    (progn (setq i 0)
      (while (< i (sslength ss))
        (setq ext (mapcar '(lambda (v) (atof (rtos v 2 3))) (cldx:ext (entget (ssname ss i)))))
        (setq cnt (cldx:inc ext cnt) i (1+ i)))))
  (setq best nil)
  (foreach c cnt (if (or (null best) (> (cdr c) (cdr best))) (setq best c)))
  (setq *cldx-pe* (if best (car best) '(0.0 0.0 1.0)))
  (write-line (strcat "HDR\tPLANE\t" (vl-princ-to-string *cldx-pe*)) f)
  (foreach v '("INSUNITS" "LUNITS" "MEASUREMENT" "EXTMIN" "EXTMAX" "DWGNAME" "ACADVER" "DIMSCALE" "LTSCALE" "UCSORG" "UCSXDIR" "UCSYDIR")
    (write-line (strcat "HDR\t" v "\t" (cldx:s (getvar v))) f))
  (foreach d (dictsearch (namedobjdict) "ACAD_LAYOUT")
    (if (= (car d) 3) (write-line (strcat "HDR\tLAYOUT\t" (cdr d)) f)))
  (setq tl (tblnext "LAYER" T))
  (while tl
    (write-line (strcat "LAY\t" (cdr (assoc 2 tl)) "\t" (itoa (cdr (assoc 62 tl))) "\t" (itoa (cdr (assoc 70 tl)))) f)
    (setq tl (tblnext "LAYER")))
  (setq cnt '())
  (if (setq ss (ssget "_X" '((410 . "Model"))))
    (progn
      (write-line (strcat "HDR\tNENT\t" (itoa (sslength ss))) f)
      (setq i 0)
      (while (< i (sslength ss))
        (setq e (ssname ss i) ed (entget e))
        (setq typ (cdr (assoc 0 ed)) lay (cdr (assoc 8 ed)))
        (setq cnt (cldx:inc (strcat lay "|" typ) cnt))
        (cldx:safe f ed "*MS" nil)
        (setq i (1+ i)))))
  (foreach c cnt (write-line (strcat "CNT\t" (car c) "\t" (itoa (cdr c))) f))
  (setq blk (tblnext "BLOCK" T))
  (while blk
    (setq bname (cdr (assoc 2 blk)) bcnt '() *cldx-bb* nil)
    (if (and (= 0 (logand 4 (cdr (assoc 70 blk)))) (not (wcmatch bname "`*D*")))
      (progn
        (setq be (cdr (assoc -2 blk)))
        (while be
          (setq bed (entget be))
          (setq bcnt (cldx:inc (cdr (assoc 0 bed)) bcnt))
          (cldx:safe f bed bname T)
          (setq be (entnext be)))
        (foreach c bcnt (write-line (strcat "BCN\t" bname "\t" (car c) "\t" (itoa (cdr c))) f))))
    (write-line (strcat "BLK\t" bname "\t" (itoa (cdr (assoc 70 blk))) "\t" (cldx:pp (cdr (assoc 10 blk))) "\t"
                        (if *cldx-bb* (strcat (cldx:r (car *cldx-bb*)) "\t" (cldx:r (cadr *cldx-bb*)) "\t" (cldx:r (caddr *cldx-bb*)) "\t" (cldx:r (cadddr *cldx-bb*))) "\t\t\t")) f)
    (setq blk (tblnext "BLOCK")))
  (close f)
  (princ "\nCLDX DUMP DONE"))
