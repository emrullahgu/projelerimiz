;;; ==========================================================================
;;; CLD_P2_05_MEKANIK.lsp
;;; PARSEL 2 - MEKANIK TESISAT (ISITMA-SOGUTMA-HAVALANDIRMA) PROJESI
;;; Isveren : BROSCO ITHALAT IHRACAT VE TICARET ANONIM SIRKETI
;;; Konum   : YUKARI MAHALLE / KEMALPASA / IZMIR
;;; Kaynak  : BROSCO 2 NOLU PARSEL MIMARI.dwg (mimari paftalar)
;;; Kullanim: APPLOAD ile yukleyin -> cizim otomatik olusur.
;;;          Yeniden cizmek icin komut: CLD_P2_MEKANIK
;;;          Tum ciktilar "CLD-P2-MEK-*" katmanlarindadir; yeniden calistirmada bu katmanlar temizlenir.
;;;          Guvenlik uyarisi gelirse "Bir kez yukle" deyin veya klasoru Secenekler > Dosyalar >
;;;          Guvenilen Konumlar (TRUSTEDPATHS) listesine ekleyin.
;;; Uretici : CLD (Claude) otomatik muhendislik motoru - tum isimler CLD onekli.
;;;   Mimari: 2 kat, 12 mahal, kat kotlari ZK=+0.00, 1K=+3.00, bina yuksekligi 11.21 m
;;;   Elektrik: kurulu 238.6 kW, talep 148.5 kW, trafo 250 kVA, KMP 90 kVAr, jenerator 45 kVA
;;;   Aydinlatma: 107 armatur, 29 priz/cikis, 46 linye, 8 pano
;;;   Topraklama: R=0.97 ohm (birlesik), paratoner LPL I, 27 inis
;;;   Mekanik: VRF 4.4 kW ic unite, dis unite 5.0 kW
;;;   Sihhi: 12 armatur, 1 pis su kolonu, 14 yagmur inisi
;;; ==========================================================================

;;; ==========================================================================
;;; CLD CORE  -  ortak cizim altyapisi (katman, stil, varlik, tablo, oynatici)
;;; Tum isimler CLD onekli. ActiveX (vla-) kullanilmaz: AutoCAD / BricsCAD /
;;; accoreconsole uyumlu saf AutoLISP + entmake.
;;; Mimari paftalar WCS XZ duzleminde (ekstruzyon 0,-1,0) cizildiginden tum
;;; varliklar ayni duzlemde (*cld-ext*) uretilir; koordinatlar pafta (OCS)
;;; koordinatidir.
;;; ==========================================================================

(setq *cld-ver* "1.0")
(if (not *cld-ext*) (setq *cld-ext* '(0.0 0.0 1.0)))
(if (not *cld-u*) (setq *cld-u* 100.0))

;;; ---------------------------------------------------------------- yardimci
(defun cld:m (x) (* x *cld-u*))
(defun cld:3d (p) (list (float (car p)) (float (cadr p)) 0.0))
(defun cld:2d (p) (list (float (car p)) (float (cadr p))))
(defun cld:pxy (p dx dy) (list (+ (car p) dx) (+ (cadr p) dy)))
(defun cld:wcs (p) (trans (cld:3d p) *cld-ext* 0))
(defun cld:top (lay) (/= lay "0"))
(defun cld:x210 (lay) (if (cld:top lay) (list (cons 210 *cld-ext*) '(410 . "Model")) '()))
;; renk / cizgi tipi / kalinlik her zaman acik yazilir: cizimdeki CECOLOR / CELTYPE / CELWEIGHT ne olursa olsun
;; katmandan (ByLayer) gelir; blok icindekiler ByBlock
(defun cld:col (lay)
  (if (= lay "0") '((62 . 0) (6 . "ByBlock") (370 . -2)) '((62 . 256) (6 . "ByLayer") (370 . -1))))
(defun cld:dlen (s / n i)
  ;; gorunen karakter sayisi (\U+XXXX = 1 karakter)
  (setq n 0 i 1)
  (while (<= i (strlen s))
    (if (and (= (substr s i 3) "\\U+") (<= (+ i 6) (strlen s))) (setq i (+ i 7)) (setq i (1+ i)))
    (setq n (1+ n)))
  n)
(defun cld:maxl (l) (if l (apply 'max l) 0))
(defun cld:sum (l) (apply '+ (cons 0 l)))
(defun cld:nth-or (i l def) (if (and l (< i (length l))) (nth i l) def))
(defun cld:range (n / i r) (setq i (1- n)) (while (>= i 0) (setq r (cons i r) i (1- i))) r)

;;; ------------------------------------------------------ tablo kayitlari
(defun cld:ltype (nm desc dash gap / sc)
  (if (not (tblsearch "LTYPE" nm))
    (progn
      (setq sc (max 1e-6 (getvar "LTSCALE")))
      (entmake (list '(0 . "LTYPE") '(100 . "AcDbSymbolTableRecord") '(100 . "AcDbLinetypeTableRecord")
                     (cons 2 nm) '(70 . 0) (cons 3 desc) '(72 . 65) '(73 . 2)
                     (cons 40 (/ (+ dash gap) sc)) (cons 49 (/ dash sc)) '(74 . 0) (cons 49 (- (/ gap sc))) '(74 . 0)))))
  nm)
(defun cld:style ()
  (if (not (tblsearch "STYLE" "CLD_YAZI"))
    (entmake '((0 . "STYLE") (100 . "AcDbSymbolTableRecord") (100 . "AcDbTextStyleTableRecord")
               (2 . "CLD_YAZI") (70 . 0) (40 . 0.0) (41 . 0.85) (50 . 0.0) (71 . 0) (42 . 2.5)
               (3 . "arial.ttf") (4 . ""))))
  "CLD_YAZI")
(defun cld:lay (nm col lt lw / e ed)
  (if (not (tblsearch "LAYER" nm))
    (entmake (list '(0 . "LAYER") '(100 . "AcDbSymbolTableRecord") '(100 . "AcDbLayerTableRecord")
                   (cons 2 nm) '(70 . 0) (cons 62 col)
                   (cons 6 (if (and lt (tblsearch "LTYPE" lt)) lt "Continuous"))
                   (cons 370 lw)))
    (progn
      (setq e (tblobjname "LAYER" nm) ed (entget e))
      (setq ed (subst (cons 70 0) (assoc 70 ed) ed))
      (setq ed (subst (cons 62 col) (assoc 62 ed) ed))
      (if (and lt (tblsearch "LTYPE" lt) (assoc 6 ed)) (setq ed (subst (cons 6 lt) (assoc 6 ed) ed)))
      (if (assoc 370 ed) (setq ed (subst (cons 370 lw) (assoc 370 ed) ed)))
      (entmod ed)))
  nm)

;;; ---------------------------------------------------- varlik olusturucular
;;; lay "0" = blok tanimi icerigi (BYBLOCK renk, blok koordinati)
(defun cld:e-line (a b lay)
  (append (list '(0 . "LINE") (cons 8 lay)) (cld:col lay)
          (if (cld:top lay) (list (cons 10 (cld:wcs a)) (cons 11 (cld:wcs b))) (list (cons 10 (cld:3d a)) (cons 11 (cld:3d b))))
          (cld:x210 lay)))
(defun cld:e-circle (c r lay)
  (append (list '(0 . "CIRCLE") (cons 8 lay)) (cld:col lay) (list (cons 10 (cld:3d c)) (cons 40 r)) (cld:x210 lay)))
(defun cld:e-arc (c r a1 a2 lay)
  (append (list '(0 . "ARC") (cons 8 lay)) (cld:col lay) (list (cons 10 (cld:3d c)) (cons 40 r) (cons 50 a1) (cons 51 a2)) (cld:x210 lay)))
(defun cld:e-pl (pts closed w lay)
  (append (list '(0 . "LWPOLYLINE") '(100 . "AcDbEntity") (cons 8 lay)) (cld:col lay)
          (list '(100 . "AcDbPolyline") (cons 90 (length pts)) (cons 70 (+ (if closed 1 0) (if (cld:top lay) 128 0))) (cons 43 w) '(38 . 0.0))
          (mapcar '(lambda (p) (cons 10 (cld:2d p))) pts)
          (cld:x210 lay)))
(defun cld:e-dot (c r lay)
  (append (list '(0 . "LWPOLYLINE") '(100 . "AcDbEntity") (cons 8 lay)) (cld:col lay)
          (list '(100 . "AcDbPolyline") '(90 . 2) '(70 . 1) (cons 43 r) '(38 . 0.0)
                (cons 10 (list (- (car c) (/ r 2.0)) (cadr c))) '(42 . 1.0)
                (cons 10 (list (+ (car c) (/ r 2.0)) (cadr c))) '(42 . 1.0))
          (cld:x210 lay)))
(defun cld:e-solid (p1 p2 p3 p4 lay)
  (append (list '(0 . "SOLID") (cons 8 lay)) (cld:col lay)
          (list (cons 10 (cld:3d p1)) (cons 11 (cld:3d p2)) (cons 12 (cld:3d p4)) (cons 13 (cld:3d p3)))
          (cld:x210 lay)))
(defun cld:e-text (p h s j lay / ed p3)
  ;; j: 0 sol-taban, 1 orta-taban, 2 sag-taban, 4 orta-orta, 7 sol-orta, 9 sag-orta
  (setq p3 (cld:3d p))
  (setq ed (append (list '(0 . "TEXT") (cons 8 lay)) (cld:col lay)
                   (list (cons 7 (cld:style)) (cons 10 p3) (cons 40 h) (cons 1 s) '(50 . 0.0) '(41 . 0.85))))
  (setq ed (cond ((= j 1) (append ed (list '(72 . 1) (cons 11 p3) '(73 . 0))))
                 ((= j 2) (append ed (list '(72 . 2) (cons 11 p3) '(73 . 0))))
                 ((= j 4) (append ed (list '(72 . 1) (cons 11 p3) '(73 . 2))))
                 ((= j 7) (append ed (list '(72 . 0) (cons 11 p3) '(73 . 2))))
                 ((= j 9) (append ed (list '(72 . 2) (cons 11 p3) '(73 . 2))))
                 (T ed)))
  (append ed (cld:x210 lay)))
(defun cld:e-ins (blk p sc rot lay)
  (append (list '(0 . "INSERT") (cons 8 lay)) (cld:col lay) (list (cons 2 blk) (cons 10 (cld:3d p))
                (cons 41 sc) (cons 42 sc) (cons 43 sc) (cons 50 rot))
          (cld:x210 lay)))
(defun cld:line (a b lay) (entmake (cld:e-line a b lay)))
(defun cld:pl (pts closed w lay) (if (cdr pts) (entmake (cld:e-pl pts closed w lay))))
(defun cld:txt (p h s j lay) (entmake (cld:e-text p h s j lay)))
(defun cld:rect (p1 p2 lay) (cld:pl (list p1 (list (car p2) (cadr p1)) p2 (list (car p1) (cadr p2))) T 0.0 lay))

;;; ------------------------------------------------------------ blok tanimi
(defun cld:defblk (name ents)
  (if (not (tblsearch "BLOCK" name))
    (progn
      (entmake (list '(0 . "BLOCK") (cons 2 name) '(70 . 0) '(10 0.0 0.0 0.0) '(8 . "0")))
      (foreach e ents (entmake e))
      (entmake '((0 . "ENDBLK") (8 . "0")))))
  name)

;;; mimari altlik blogu: plines ((kapali (x y) (x y) ...) ...)  texts ((x y h "yazi") ...)
(defun cld:defblk-bg (name plines texts)
  (if (not (tblsearch "BLOCK" name))
    (progn
      (entmake (list '(0 . "BLOCK") (cons 2 name) '(70 . 0) '(10 0.0 0.0 0.0) '(8 . "0")))
      (foreach p plines (if (cddr p) (entmake (cld:e-pl (cdr p) (car p) 0.0 "0"))))
      (foreach s texts (entmake (cld:e-text (list (car s) (cadr s)) (caddr s) (cadddr s) 4 "0")))
      (entmake '((0 . "ENDBLK") (8 . "0")))))
  name)

;;; ------------------------------------------------------------------ tablo
;;; rows: ((hucre ...) ...)  ilk satir baslik. Sutun genislikleri otomatik.
(defun cld:table (org title rows h lay / ncol widths rh y x w i r cw tw pad s)
  (setq pad (* 0.6 h) rh (* 2.0 h))
  (setq ncol (cld:maxl (mapcar 'length rows)))
  (setq widths (mapcar '(lambda (c)
                          (+ (* 2 pad) (* 0.66 h (cld:maxl (mapcar '(lambda (r) (cld:dlen (cld:nth-or c r ""))) rows)))))
                       (cld:range ncol)))
  (setq tw (cld:sum widths) x (car org) y (cadr org))
  (if (and title (/= title ""))
    (progn
      (cld:rect (list x y) (list (+ x tw) (- y (* 1.5 rh))) lay)
      (cld:txt (list (+ x pad) (- y (* 0.75 rh))) (* 1.3 h) title 7 lay)
      (setq y (- y (* 1.5 rh)))))
  (setq i 0)
  (foreach r rows
    (setq x (car org) cw 0)
    (cld:rect (list x y) (list (+ x tw) (- y rh)) lay)
    (foreach w widths
      (if (> cw 0) (cld:line (list x y) (list x (- y rh)) lay))
      (setq s (cld:nth-or cw r ""))
      (if (/= s "") (cld:txt (list (+ x pad) (- y (* 0.5 rh))) h s 7 lay))
      (setq x (+ x w) cw (1+ cw)))
    (if (= i 0) (cld:pl (list (list (car org) (- y rh)) (list (+ (car org) tw) (- y rh))) nil (* 0.12 h) lay))
    (setq y (- y rh) i (1+ i)))
  (list (- y (* 2.0 h)) tw))
(defun cld:notes (org title lines h lay / y)
  (setq y (cadr org))
  (if (and title (/= title "")) (progn (cld:txt (list (car org) y) (* 1.3 h) title 0 lay) (setq y (- y (* 2.2 h)))))
  (foreach s lines (cld:txt (list (car org) y) h s 0 lay) (setq y (- y (* 1.7 h))))
  (- y h))

;;; ------------------------------------------------------------- oynatici
;;; Hesap motorunun urettigi cizim komutlari:
;;;  ("LY" ad renk cizgitipi kalinlik)        katman
;;;  ("I" lay blok x y aci olcek)             sembol (olcek * *cld-u*)
;;;  ("L" lay x1 y1 x2 y2)                    cizgi
;;;  ("P" lay kapali genislik ((x y) ...))    polyline
;;;  ("C" lay x y r)                          daire
;;;  ("D" lay x y r)                          dolu daire
;;;  ("T" lay x y h hiza "yazi")              yazi
;;;  ("TB" lay x y h "baslik" satirlar)       tablo
;;;  ("NT" lay x y h "baslik" satirlar)       not blogu
(defun cld:op (o / k)
  (setq k (car o))
  (cond ((= k "I") (entmake (cld:e-ins (nth 2 o) (list (nth 3 o) (nth 4 o)) (* (nth 6 o) *cld-u*) (nth 5 o) (nth 1 o))))
        ((= k "L") (cld:line (list (nth 2 o) (nth 3 o)) (list (nth 4 o) (nth 5 o)) (nth 1 o)))
        ((= k "P") (cld:pl (nth 4 o) (nth 2 o) (nth 3 o) (nth 1 o)))
        ((= k "C") (entmake (cld:e-circle (list (nth 2 o) (nth 3 o)) (nth 4 o) (nth 1 o))))
        ((= k "D") (entmake (cld:e-dot (list (nth 2 o) (nth 3 o)) (nth 4 o) (nth 1 o))))
        ((= k "T") (cld:txt (list (nth 2 o) (nth 3 o)) (nth 4 o) (nth 6 o) (nth 5 o) (nth 1 o)))
        ((= k "TB") (cld:table (list (nth 2 o) (nth 3 o)) (nth 5 o) (nth 6 o) (nth 4 o) (nth 1 o)))
        ((= k "NT") (cld:notes (list (nth 2 o) (nth 3 o)) (nth 5 o) (nth 6 o) (nth 4 o) (nth 1 o)))
        ((= k "LY") (cld:lay (nth 1 o) (nth 2 o) (nth 3 o) (nth 4 o)))
        ((= k "BK") (cld:defblk-bg (nth 1 o) (nth 2 o) (nth 3 o)))))
(defun cld:play (ops / r)
  (foreach o ops
    (setq r (vl-catch-all-apply 'cld:op (list o)))
    (cond ((vl-catch-all-error-p r) (setq *cld-bad* (cons (list (car o) (nth 1 o) (vl-catch-all-error-message r)) *cld-bad*)))
          ((and (null r) (or (member (car o) '("I" "L" "C" "D" "T")) (and (= (car o) "P") (cdr (nth 4 o)))))
           (setq *cld-bad* (cons (list (car o) (nth 1 o) (if (= (car o) "I") (nth 2 o) "")) *cld-bad*)))
          (T (setq *cld-n* (1+ *cld-n*))))))

;;; ------------------------------------------------------- calisma ortami
(defun cld:clear (pat / ss i n)
  (setq n 0)
  (if (setq ss (ssget "_X" (list (cons 8 pat))))
    (progn (setq i 0) (while (< i (sslength ss)) (entdel (ssname ss i)) (setq i (1+ i) n (1+ n)))))
  n)
(defun cld:begin (pat)
  (setq *cld-old* (list (getvar "CMDECHO") (getvar "OSMODE")) *cld-n* 0 *cld-bad* nil)
  (setvar "CMDECHO" 0)
  (setvar "OSMODE" 0)
  ;; cizim model alaninda olusur (bir yerlesim sekmesi acik olsa bile)
  (if (= 0 (getvar "TILEMODE")) (vl-catch-all-apply 'setvar (list "TILEMODE" 1)))
  (vl-catch-all-apply 'command-s (list "_.UNDO" "_BEGIN"))
  (cld:style)
  (cld:ltype "CLD_KESIK" "CLD kesik __ __" (cld:m 0.30) (cld:m 0.15))
  (cld:ltype "CLD_NOKTALI" "CLD noktali . . ." (cld:m 0.05) (cld:m 0.10))
  (cld:ltype "CLD_UZUNKESIK" "CLD uzun kesik ____ ____" (cld:m 0.80) (cld:m 0.20)))
;;; disiplin katmanlarinin kilidini kaldir / coz (eski cikti silinebilsin)
(defun cld:unlock (pat / tl ed)
  (setq tl (tblnext "LAYER" T))
  (while tl
    (if (and (wcmatch (cdr (assoc 2 tl)) pat) (/= 0 (logand 5 (cdr (assoc 70 tl)))))
      (progn (setq ed (entget (tblobjname "LAYER" (cdr (assoc 2 tl)))))
             (entmod (subst (cons 70 0) (assoc 70 ed) ed))))
    (setq tl (tblnext "LAYER"))))
(defun cld:restore ()
  (vl-catch-all-apply 'command-s (list "_.UNDO" "_END"))
  (if *cld-old* (progn (setvar "CMDECHO" (car *cld-old*)) (setvar "OSMODE" (cadr *cld-old*))))
  (setq *cld-old* nil))
(defun cld:first5 (l / r i) (setq i 0) (foreach x l (if (< i 5) (setq r (cons x r))) (setq i (1+ i))) (reverse r))
(defun cld:end (msg)
  (cld:restore)
  (princ (strcat "\n" msg " (" (itoa *cld-n*) " varlik/komut)"))
  (if *cld-bad*
    (progn
      (princ (strcat "\nCLD UYARI: " (itoa (length *cld-bad*)) " varlik olusturulamadi, ilkleri:"))
      (foreach b (cld:first5 (reverse *cld-bad*)) (princ (strcat "\n   " (vl-princ-to-string b))))))
  (princ))
;;; acik cizim baska bir parsele mi ait? (dosya adinda baska parselin "<n> NOLU" ifadesi)
(defun cld:wrong-dwg (parcel others / nm bad)
  (setq nm (strcase (getvar "DWGNAME")))
  (foreach o others (if (wcmatch nm (strcat "* " o " NOLU*,BROSCO " o " *,P" o ".DWG")) (setq bad T)))
  (and bad (not (wcmatch nm (strcat "* " parcel " NOLU*,BROSCO " parcel " *,P" parcel ".DWG")))))
(defun cld:err (m)
  (cld:restore)
  (if (not (member m '("Function cancelled" "quit / exit abort"))) (princ (strcat "\nCLD HATA: " m)))
  (princ))


;;; ==========================================================================
;;; CLD SEMBOL KUTUPHANESI - bloklar 1 birim = 1 m tanimlanir, cizime
;;; (olcek x *cld-u*) ile yerlestirilir. Duvar sembollerinde duvar yerel x=0,
;;; sembol +X yonune (mahal icine) bakar.
;;; ==========================================================================

(defun cld:b-box (w h)
  (cld:e-pl (list (list (- (/ w 2)) (- (/ h 2))) (list (/ w 2) (- (/ h 2))) (list (/ w 2) (/ h 2)) (list (- (/ w 2)) (/ h 2))) T 0.0 "0"))
(defun cld:b-wallbox (d w)
  (cld:e-pl (list (list 0.0 (- (/ w 2))) (list d (- (/ w 2))) (list d (/ w 2)) (list 0.0 (/ w 2))) T 0.0 "0"))
(defun cld:b-x (r)
  (list (cld:e-line (list (- r) (- r)) (list r r) "0") (cld:e-line (list (- r) r) (list r (- r)) "0")))
(defun cld:b-txt (p h s) (cld:e-text p h s 4 "0"))

(defun cld:def-symbols ( / r)
  ;; ---------------- AYDINLATMA
  (setq r 0.12)
  (cld:defblk "CLD_S_DL" (append (list (cld:e-circle '(0 0) r "0")) (cld:b-x (* r 0.707))))
  (cld:defblk "CLD_S_DLB" (append (list (cld:e-circle '(0 0) r "0") (cld:e-circle '(0 0) (* r 1.35) "0")) (cld:b-x (* r 0.707))))
  (cld:defblk "CLD_S_HB" (append (list (cld:e-circle '(0 0) 0.30 "0") (cld:e-circle '(0 0) 0.12 "0")) (cld:b-x 0.21)))
  (cld:defblk "CLD_S_PNL" (append (list (cld:b-box 0.6 0.6)) (cld:b-x 0.3)))
  (cld:defblk "CLD_S_ETJ" (list (cld:b-box 1.2 0.2) (cld:e-line '(-0.6 0.0) '(0.6 0.0) "0")
                                (cld:e-line '(-0.5 -0.1) '(-0.5 0.1) "0") (cld:e-line '(0.5 -0.1) '(0.5 0.1) "0")))
  (cld:defblk "CLD_S_PLF" (list (cld:e-circle '(0 0) 0.15 "0") (cld:e-dot '(0 0) 0.07 "0")))
  (cld:defblk "CLD_S_ACIL" (list (cld:b-box 0.32 0.16) (cld:e-solid '(-0.16 -0.08) '(0.16 -0.08) '(0.16 0.08) '(0.16 0.08) "0")))
  (cld:defblk "CLD_S_EXIT" (list (cld:b-box 0.40 0.20) (cld:e-line '(-0.14 0) '(0.12 0) "0") (cld:e-line '(0.12 0) '(0.04 0.06) "0")
                                 (cld:e-line '(0.12 0) '(0.04 -0.06) "0")))
  (cld:defblk "CLD_S_PRJ" (list (cld:e-pl '((-0.15 -0.10) (0.15 -0.10) (0.22 0.12) (-0.22 0.12)) T 0.0 "0") (cld:e-line '(-0.15 0.0) '(0.15 0.0) "0")))
  (cld:defblk "CLD_S_BOLLARD" (list (cld:e-circle '(0 0) 0.12 "0") (cld:e-dot '(0 0) 0.12 "0")))
  ;; ---------------- PRIZ / ANAHTAR (duvar sembolleri)
  (cld:defblk "CLD_S_PRIZ" (list (cld:e-line '(0 0) '(0.06 0) "0") (cld:e-line '(0.06 -0.12) '(0.06 0.12) "0")
                                 (cld:e-arc '(0.06 0) 0.12 (- (/ pi 2)) (/ pi 2) "0") (cld:e-line '(0.20 -0.10) '(0.20 0.10) "0")))
  (cld:defblk "CLD_S_PRIZE" (list (cld:e-line '(0 0) '(0.06 0) "0") (cld:e-line '(0.06 -0.12) '(0.06 0.12) "0")
                                  (cld:e-arc '(0.06 0) 0.12 (- (/ pi 2)) (/ pi 2) "0") (cld:e-dot '(0.11 0) 0.06 "0")
                                  (cld:e-line '(0.20 -0.10) '(0.20 0.10) "0")))
  (cld:defblk "CLD_S_PRIZU" (list (cld:e-line '(0 0) '(0.06 0) "0") (cld:e-line '(0.06 -0.12) '(0.06 0.12) "0")
                                  (cld:e-arc '(0.06 0) 0.12 (- (/ pi 2)) (/ pi 2) "0") (cld:b-txt '(0.11 0) 0.09 "U")))
  (cld:defblk "CLD_S_PRIZ3" (list (cld:e-line '(0 0) '(0.06 0) "0") (cld:e-line '(0.06 -0.14) '(0.06 0.14) "0")
                                  (cld:e-arc '(0.06 0) 0.14 (- (/ pi 2)) (/ pi 2) "0")
                                  (cld:e-line '(0.10 -0.06) '(0.18 -0.06) "0") (cld:e-line '(0.10 0.0) '(0.18 0.0) "0") (cld:e-line '(0.10 0.06) '(0.18 0.06) "0")))
  (cld:defblk "CLD_S_PGRUP" (list (cld:b-box 0.50 0.30) (cld:e-arc '(-0.13 -0.02) 0.08 0.0 pi "0") (cld:e-arc '(0.0 -0.02) 0.08 0.0 pi "0")
                                  (cld:e-arc '(0.13 -0.02) 0.08 0.0 pi "0") (cld:e-line '(-0.25 -0.08) '(0.25 -0.08) "0")))
  (foreach c '(("CLD_S_CK_KLIMA" "K") ("CLD_S_CK_FIRIN" "F") ("CLD_S_CK_BULASIK" "B") ("CLD_S_CK_CAMASIR" "\\U+00C7")
               ("CLD_S_CK_KURUTMA" "KM") ("CLD_S_CK_KOMBI" "KB") ("CLD_S_CK_DAVLUMBAZ" "D") ("CLD_S_CK_POMPA" "P")
               ("CLD_S_CK_ASPIRATOR" "A") ("CLD_S_CK_ASANSOR" "AS") ("CLD_S_CK_SARJ" "EV") ("CLD_S_CK_ISITICI" "IS")
               ("CLD_S_CK_TERMOSIFON" "TS") ("CLD_S_CK_MAKINE" "M"))
    (cld:defblk (car c) (list (cld:b-wallbox 0.24 0.24) (cld:e-solid '(0 -0.12) '(0.08 -0.12) '(0.08 0.12) '(0 0.12) "0")
                              (cld:b-txt '(0.16 0.0) 0.09 (cadr c)))))
  (cld:defblk "CLD_S_ANH1" (list (cld:e-circle '(0.10 0) 0.05 "0") (cld:e-line '(0.135 0.035) '(0.25 0.15) "0") (cld:e-line '(0.25 0.15) '(0.29 0.11) "0")))
  (cld:defblk "CLD_S_ANH2" (list (cld:e-circle '(0.10 0) 0.05 "0") (cld:e-line '(0.135 0.035) '(0.25 0.15) "0") (cld:e-line '(0.25 0.15) '(0.29 0.11) "0")
                                 (cld:e-line '(0.135 -0.035) '(0.25 -0.15) "0") (cld:e-line '(0.25 -0.15) '(0.29 -0.11) "0")))
  (cld:defblk "CLD_S_VAV" (list (cld:e-circle '(0.10 0) 0.05 "0") (cld:e-line '(0.135 0.035) '(0.25 0.15) "0") (cld:e-line '(0.25 0.15) '(0.29 0.11) "0")
                                (cld:e-line '(0.065 -0.035) '(-0.05 -0.15) "0") (cld:e-line '(-0.05 -0.15) '(-0.09 -0.11) "0")))
  (cld:defblk "CLD_S_BUAT" (list (cld:e-circle '(0 0) 0.05 "0")))
  ;; ---------------- PANOLAR
  (cld:defblk "CLD_S_TP" (list (cld:b-wallbox 0.16 0.50) (cld:e-solid '(0 -0.25) '(0.16 -0.25) '(0.16 0.25) '(0 -0.25) "0")))
  (cld:defblk "CLD_S_ADP" (list (cld:b-wallbox 0.30 0.90) (cld:e-solid '(0 -0.45) '(0.30 -0.45) '(0.30 0.45) '(0 0.45) "0")))
  (cld:defblk "CLD_S_KMP" (list (cld:b-wallbox 0.30 0.60) (cld:e-line '(0 -0.30) '(0.30 0.30) "0") (cld:b-txt '(0.15 -0.15) 0.10 "C")))
  (cld:defblk "CLD_S_KOLON" (list (cld:e-circle '(0 0) 0.15 "0") (cld:e-line '(-0.106 -0.106) '(0.106 0.106) "0")
                                  (cld:e-line '(0.106 0.106) '(0.02 0.106) "0") (cld:e-line '(0.106 0.106) '(0.106 0.02) "0")))
  (cld:defblk "CLD_S_OAP" (list (cld:b-wallbox 0.20 0.60) (cld:e-solid '(0 -0.30) '(0.20 -0.30) '(0.20 0.0) '(0 0.0) "0")))
  (cld:defblk "CLD_S_TRAFO" (list (cld:b-box 6.0 5.0) (cld:e-circle '(-0.45 0) 0.8 "0") (cld:e-circle '(0.45 0) 0.8 "0")))
  (cld:defblk "CLD_S_JEN" (list (cld:b-box 4.0 1.6) (cld:e-circle '(-1.2 0) 0.55 "0") (cld:b-txt '(-1.2 0) 0.5 "G")))
  ;; ---------------- TOPRAKLAMA / PARATONER
  (cld:defblk "CLD_S_TOP_FILIZ" (list (cld:e-circle '(0 0) 0.15 "0") (cld:e-dot '(0 0) 0.12 "0")))
  (cld:defblk "CLD_S_TOP_EPB" (list (cld:b-box 0.60 0.16) (cld:e-solid '(-0.30 -0.08) '(0.30 -0.08) '(0.30 0.08) '(-0.30 0.08) "0")
                                    (cld:e-line '(-0.2 -0.08) '(-0.2 -0.25) "0") (cld:e-line '(0 -0.08) '(0 -0.25) "0") (cld:e-line '(0.2 -0.08) '(0.2 -0.25) "0")))
  (cld:defblk "CLD_S_TOP_YEB" (list (cld:b-wallbox 0.10 0.30) (cld:e-solid '(0 -0.15) '(0.10 -0.15) '(0.10 0.15) '(0 0.15) "0")))
  (cld:defblk "CLD_S_TOP_KAZIK" (list (cld:e-line '(0 0.20) '(0 0) "0") (cld:e-line '(-0.15 0) '(0.15 0) "0")
                                      (cld:e-line '(-0.10 -0.05) '(0.10 -0.05) "0") (cld:e-line '(-0.05 -0.10) '(0.05 -0.10) "0")
                                      (cld:e-circle '(0 0.05) 0.25 "0")))
  (cld:defblk "CLD_S_TOP_OLCU" (append (list (cld:b-box 0.30 0.30)) (cld:b-x 0.15)))
  (cld:defblk "CLD_S_PAR_UC" (list (cld:e-circle '(0 0) 0.20 "0") (cld:e-solid '(-0.12 -0.08) '(0.12 -0.08) '(0.0 0.14) '(0.0 0.14) "0")))
  (cld:defblk "CLD_S_PAR_INIS" (list (cld:e-circle '(0 0) 0.15 "0") (cld:e-dot '(0 0) 0.08 "0")
                                     (cld:e-line '(0.0 -0.15) '(0.0 -0.40) "0") (cld:e-line '(-0.08 -0.30) '(0.0 -0.40) "0") (cld:e-line '(0.08 -0.30) '(0.0 -0.40) "0")))
  (cld:defblk "CLD_S_PAR_KLEMENS" (list (cld:b-box 0.25 0.25) (cld:e-solid '(-0.125 -0.125) '(0.125 -0.125) '(0.125 0.125) '(-0.125 -0.125) "0")))
  ;; ---------------- MEKANIK
  (cld:defblk "CLD_S_KASET" (append (list (cld:b-box 0.84 0.84) (cld:b-box 0.56 0.56)) (cld:b-x 0.28)))
  (cld:defblk "CLD_S_VRFOUT" (list (cld:b-box 1.30 0.75) (cld:e-circle '(-0.3 0) 0.28 "0") (cld:e-circle '(0.3 0) 0.28 "0")))
  (cld:defblk "CLD_S_HRV" (list (cld:b-box 1.40 0.80) (cld:e-line '(-0.7 -0.4) '(0.7 0.4) "0") (cld:e-line '(-0.7 0.4) '(0.7 -0.4) "0") (cld:b-txt '(0 0.25) 0.15 "HRV")))
  (cld:defblk "CLD_S_MENFEZ" (append (list (cld:b-box 0.60 0.60) (cld:b-box 0.30 0.30)) (cld:b-x 0.30)))
  (cld:defblk "CLD_S_EMIS" (list (cld:b-box 0.40 0.40) (cld:e-line '(-0.2 -0.1) '(0.2 -0.1) "0") (cld:e-line '(-0.2 0.0) '(0.2 0.0) "0") (cld:e-line '(-0.2 0.1) '(0.2 0.1) "0")))
  (cld:defblk "CLD_S_CATIFAN" (list (cld:e-circle '(0 0) 0.60 "0") (cld:e-circle '(0 0) 0.15 "0") (cld:e-line '(0 0) '(0.5 0.25) "0")
                                    (cld:e-line '(0 0) '(-0.5 0.25) "0") (cld:e-line '(0 0) '(0 -0.55) "0")))
  (cld:defblk "CLD_S_PANJUR" (list (cld:b-wallbox 0.20 1.20) (cld:e-line '(0 -0.4) '(0.2 -0.3) "0") (cld:e-line '(0 0.0) '(0.2 0.1) "0") (cld:e-line '(0 0.4) '(0.2 0.5) "0")))
  (cld:defblk "CLD_S_RADYANT" (list (cld:e-pl '((-3.0 -0.15) (3.0 -0.15) (3.0 0.15) (-3.0 0.15)) T 0.0 "0") (cld:e-line '(-3.0 0) '(2.6 0) "0") (cld:b-box 0.6 0.4)))
  (cld:defblk "CLD_S_SIGFAN" (list (cld:b-box 0.80 0.60) (cld:e-circle '(0 0) 0.22 "0") (cld:b-txt '(0 -0.2) 0.10 "S")))
  ;; ---------------- SIHHI TESISAT
  (cld:defblk "CLD_S_PK" (append (list (cld:e-circle '(0 0) 0.10 "0")) (cld:b-x 0.07)))
  (cld:defblk "CLD_S_TSK" (list (cld:e-circle '(0 0) 0.08 "0") (cld:e-dot '(0 0) 0.05 "0")))
  (cld:defblk "CLD_S_YK" (list (cld:e-circle '(0 0) 0.10 "0") (cld:e-circle '(0 0) 0.05 "0")))
  (cld:defblk "CLD_S_YS" (list (cld:b-box 0.18 0.18) (cld:e-circle '(0 0) 0.06 "0") (cld:e-line '(-0.06 0) '(0.06 0) "0")))
  (cld:defblk "CLD_S_SUSAYAC" (list (cld:e-circle '(0 0) 0.12 "0") (cld:e-line '(-0.12 0) '(0.12 0) "0") (cld:b-txt '(0 0.05) 0.06 "m3")))
  (cld:defblk "CLD_S_ROGAR" (list (cld:b-box 0.60 0.60) (cld:e-circle '(0 0) 0.22 "0")))
  (cld:defblk "CLD_S_DEPO" (append (list (cld:b-box 1.20 0.80)) (list (cld:e-line '(-0.6 -0.4) '(0.6 0.4) "0") (cld:e-line '(-0.6 0.4) '(0.6 -0.4) "0"))))
  (cld:defblk "CLD_S_KLOZET" (list (cld:e-pl '((-0.18 0.30) (0.18 0.30) (0.18 0.12) (-0.18 0.12)) T 0.0 "0")
                                   (cld:e-circle '(0 -0.08) 0.18 "0")))
  (cld:defblk "CLD_S_LAVABO" (list (cld:b-box 0.50 0.40) (cld:e-circle '(0 -0.03) 0.13 "0")))
  (cld:defblk "CLD_S_ABDEST" (list (cld:b-box 0.40 0.30) (cld:e-circle '(0 0.05) 0.05 "0") (cld:e-line '(0 0.05) '(0 -0.12) "0")))
  (cld:defblk "CLD_S_YD" (list (cld:b-wallbox 0.25 0.80) (cld:e-solid '(0 -0.40) '(0.25 -0.40) '(0.25 -0.10) '(0 -0.10) "0")
                              (cld:b-txt '(0.125 0.15) 0.12 "YD")))
  (cld:defblk "CLD_S_DUS" (append (list (cld:b-box 0.90 0.90) (cld:e-circle '(0 0) 0.06 "0")) (cld:b-x 0.45)))
  T)


(setq *cld-u* 100.0)
(setq *cld-ext* (list 0.0 0.0 1.0))

(defun cld:ops-p2_mekanik-layers () (cld:play (quote (("LY" "CLD-P2-MEK-YAZI" 7 nil -3) ("LY" "CLD-P2-MEK-PAFTA" 7 nil 50) ("LY" "CLD-P2-MEK-ALTLIK" 8 nil 13) ("LY" "CLD-P2-MEK-TABLO" 7 nil -3) ("LY" "CLD-P2-MEK-VRF" 5 nil -3) ("LY" "CLD-P2-MEK-SOGUTUCU" 6 "CLD_NOKTALI" 18) ("LY" "CLD-P2-MEK-KANAL-TAZE" 4 "CLD_KESIK" 25) ("LY" "CLD-P2-MEK-KANAL-EGZOZ" 3 "CLD_UZUNKESIK" 25) ("LY" "CLD-P2-MEK-FAN-PANJUR" 2 nil -3) ("LY" "CLD-P2-MEK-ISITICI" 1 nil -3)))))
(defun cld:ops-p2_mekanik-1 () (cld:play (quote (
   ("BK" "CLD_P2_MIMARI_1K_V2" ((nil (7250.3 7995.7) (7341.0 7995.7)) (nil (7271.6 7979.5) (7271.6 8011.8)) (T (7282.4 7995.7) (7282.0 7998.5) (7280.9 8001.1) (7279.2 8003.3) (7277.0 8005.0) (7274.4 8006.1) (7271.6 8006.4) (7268.8 8006.1) (7266.2 8005.0) (7264.0 8003.3) (7262.2 8001.1) (7261.2 7998.5) (7260.8 7995.7) (7261.2 7992.9) (7262.2 7990.3) (7264.0 7988.0) (7266.2 7986.3) (7268.8 7985.2) (7271.6 7984.9) (7274.4 7985.2) (7277.0 7986.3) (7279.2 7988.0) (7280.9 7990.3) (7282.0 7992.9) (7282.4 7995.7)) (nil (7176.3 8201.6) (7267.0 8201.6)) (nil (7197.5 8185.4) (7197.5 8217.8)) (T (7208.3 8201.6) (7207.9 8204.4) (7206.9 8207.0) (7205.2 8209.2) (7202.9 8210.9) (7200.3 8212.0) (7197.5 8212.4) (7194.7 8212.0) (7192.1 8210.9) (7189.9 8209.2) (7188.2 8207.0) (7187.1 8204.4) (7186.7 8201.6) (7187.1 8198.8) (7188.2 8196.2) (7189.9 8193.9) (7192.1 8192.2) (7194.7 8191.2) (7197.5 8190.8) (7200.3 8191.2) (7202.9 8192.2) (7205.2 8193.9) (7206.9 8196.2) (7207.9 8198.8) (7208.3 8201.6)) (nil (7329.4 7939.8) (7325.4 7939.8)) (nil (7329.4 7924.8) (7329.4 7939.8)) (nil (7239.4 7924.8) (7239.4 7939.8)) (nil (7322.6 7845.4) (7326.6 7845.4)) (nil (7322.6 7924.8) (7322.6 7845.4)) (nil (7326.6 7845.4) (7326.6 7924.8)) (nil (7325.4 7928.8) (7325.4 7939.8)) (nil (7326.6 7928.8) (7325.4 7928.8)) (nil (7326.6 7924.8) (7326.6 7928.8)) (nil (7329.4 7924.8) (7326.6 7924.8)) (nil (7329.4 7939.8) (7329.4 7924.8)) (nil (7239.4 7939.8) (7243.4 7939.8)) (nil (7239.4 7924.8) (7239.4 7939.8)) (nil (7242.2 7924.8) (7239.4 7924.8)) (nil (7242.2 7928.8) (7242.2 7924.8)) (nil (7243.4 7928.8) (7242.2 7928.8)) (nil (7243.4 7939.8) (7243.4 7928.8)) (nil (7242.2 7924.8) (7252.8 7896.0) (7271.8 7871.7) (7297.1 7854.3) (7326.6 7845.4)) (nil (7239.4 7924.8) (7239.4 7939.8)) (nil (7329.4 7924.8) (7329.4 7939.8)) (nil (7329.4 7939.8) (7329.4 7924.8)) (nil (7329.4 8059.8) (7325.4 8059.8)) (nil (7329.4 8074.8) (7329.4 8059.8)) (nil (7239.4 8074.8) (7239.4 8059.8)) (nil (7322.6 8154.2) (7326.6 8154.2)) (nil (7322.6 8074.8) (7322.6 8154.2)) (nil (7326.6 8154.2) (7326.6 8074.8)) (nil (7325.4 8070.8) (7325.4 8059.8)) (nil (7326.6 8070.8) (7325.4 8070.8)) (nil (7326.6 8074.8) (7326.6 8070.8)) (nil (7329.4 8074.8) (7326.6 8074.8)) (nil (7329.4 8059.8) (7329.4 8074.8)) (nil (7239.4 8059.8) (7243.4 8059.8)) (nil (7239.4 8074.8) (7239.4 8059.8)) (nil (7242.2 8074.8) (7239.4 8074.8)) (nil (7242.2 8070.8) (7242.2 8074.8)) (nil (7243.4 8070.8) (7242.2 8070.8)) (nil (7243.4 8059.8) (7243.4 8070.8)) (nil (7326.6 8154.2) (7297.1 8145.4) (7271.8 8128.0) (7252.8 8103.7) (7242.2 8074.8)) (nil (7239.4 8074.8) (7239.4 8059.8)) (nil (7329.4 8074.8) (7329.4 8059.8)) (nil (7330.5 8074.8) (7330.5 8082.1)) (nil (7020.1 8074.8) (7016.1 8074.8)) (nil (7020.1 8059.8) (7020.1 8074.8)) (nil (6930.1 8059.8) (6930.1 8074.8)) (nil (7013.3 7980.4) (7017.3 7980.4)) (nil (7013.3 8059.8) (7013.3 7980.4)) (nil (7017.3 7980.4) (7017.3 8059.8)) (nil (7016.1 8063.8) (7016.1 8074.8)) (nil (7017.3 8063.8) (7016.1 8063.8)) (nil (7017.3 8059.8) (7017.3 8063.8)) (nil (7020.1 8059.8) (7017.3 8059.8)) (nil (7020.1 8074.8) (7020.1 8059.8)) (nil (6930.1 8074.8) (6934.1 8074.8)) (nil (6930.1 8059.8) (6930.1 8074.8)) (nil (6932.9 8059.8) (6930.1 8059.8)) (nil (6932.9 8063.8) (6932.9 8059.8)) (nil (6934.1 8063.8) (6932.9 8063.8)) (nil (6934.1 8074.8) (6934.1 8063.8)) (nil (6932.9 8059.8) (6943.5 8030.9) (6962.5 8006.6) (6987.8 7989.2) (7017.3 7980.4)) (nil (6930.1 8059.8) (6930.1 8074.8)) (nil (7020.1 8059.8) (7020.1 8074.8)) (nil (7021.2 8059.8) (7021.2 8052.4)) (nil (7200.1 7924.8) (7196.1 7924.8)) (nil (7200.1 7939.8) (7200.1 7924.8)) (nil (7110.1 7939.8) (7110.1 7924.8)) (nil (7193.3 8019.2) (7197.3 8019.2)) (nil (7193.3 7939.8) (7193.3 8019.2)) (nil (7197.3 8019.2) (7197.3 7939.8)) (nil (7196.1 7935.8) (7196.1 7924.8)) (nil (7197.3 7935.8) (7196.1 7935.8)) (nil (7197.3 7939.8) (7197.3 7935.8)) (nil (7200.1 7939.8) (7197.3 7939.8)) (nil (7200.1 7924.8) (7200.1 7939.8)) (nil (7110.1 7924.8) (7114.1 7924.8)) (nil (7110.1 7939.8) (7110.1 7924.8)) (nil (7112.9 7939.8) (7110.1 7939.8)) (nil (7112.9 7935.8) (7112.9 7939.8)) (nil (7114.1 7935.8) (7112.9 7935.8)) (nil (7114.1 7924.8) (7114.1 7935.8)) (nil (7197.3 8019.2) (7167.9 8010.4) (7142.5 7993.0) (7123.6 7968.7) (7112.9 7939.8)) (nil (7110.1 7939.8) (7110.1 7924.8)) (nil (7200.1 7939.8) (7200.1 7924.8)) (nil (7201.3 7939.8) (7201.3 7947.1)) (nil (7035.1 7939.8) (7035.1 8059.8)) (nil (7020.1 7939.8) (7020.1 8059.8)) (nil (7329.4 8059.8) (7329.4 8074.8)) (nil (7200.1 7924.8) (7242.2 7924.8)) (nil (7325.4 7939.8) (7542.7 7939.8)) (nil (7226.4 7939.8) (7243.4 7939.8)) (nil (7193.3 7939.8) (7211.4 7939.8)) (nil (6843.9 7939.8) (7112.9 7939.8)) (nil (7322.7 8074.8) (7406.4 8074.9)) (nil (7016.1 8074.8) (7242.2 8074.8)) (nil (6883.3 8074.7) (6934.1 8074.7)) (nil (7329.4 8059.8) (7421.5 8059.9)) (nil (7226.4 8059.8) (7239.4 8059.8)) (nil (7013.3 8059.8) (7211.4 8059.8)) (nil (6883.3 8059.7) (6932.9 8059.7)) (nil (7541.4 7939.8) (7520.0 7939.8)) (nil (7211.4 8059.8) (7211.4 7939.8)) (nil (7226.4 8059.8) (7226.4 7939.8)) (nil (7346.4 8059.8) (7346.4 7939.8)) (nil (7371.4 8059.8) (7371.4 7939.8)) (nil (7396.4 8059.8) (7396.4 7939.8)) (nil (7421.4 8059.8) (7421.4 7939.8)) (nil (7421.4 8084.8) (7531.4 8084.8)) (nil (7421.4 8109.8) (7531.4 8109.8)) (nil (7421.4 8134.8) (7531.4 8134.8)) (nil (7421.4 8159.8) (7531.4 8159.8)) (nil (7421.4 8184.8) (7531.4 8184.8)) (nil (7421.4 8209.8) (7531.4 8209.8)) (nil (7421.4 8234.8) (7531.4 8234.8)) (nil (7421.4 8259.8) (7531.4 8259.8)) (nil (7421.4 8284.8) (7531.4 8284.8)) (nil (7421.4 8309.8) (7531.4 8309.8)) (nil (7421.4 8334.8) (7541.4 8334.8)) (nil (7421.4 8059.8) (7421.4 8049.8)) (nil (7541.4 8059.8) (7421.4 8059.8)) (nil (7421.4 8059.8) (7421.4 8049.8)) (nil (7421.4 8059.8) (7421.4 8049.8)) (nil (7421.4 8084.8) (7541.4 8084.8)) (nil (7421.4 8109.8) (7541.4 8109.8)) (nil (7421.4 8134.8) (7541.4 8134.8)) (nil (7421.4 8159.8) (7541.4 8159.8)) (nil (7421.4 8184.8) (7541.4 8184.8)) (nil (7421.4 8209.8) (7541.4 8209.8)) (nil (7421.4 8234.8) (7541.4 8234.8)) (nil (7421.4 8259.8) (7541.4 8259.8)) (nil (7421.4 8284.8) (7541.4 8284.8)) (nil (7421.4 8309.8) (7541.4 8309.8)) (nil (7421.4 8334.8) (7538.4 8334.8)) (nil (7421.4 8059.8) (7421.4 8334.8)) (nil (7421.4 8304.8) (7421.4 8319.8)) (nil (8693.0 2066.9) (6345.8 5352.9) (1517.3 6484.5) (1058.6 6932.1) (5479.1 8059.4) (5998.2 8156.3) (7170.0 8375.1) (7688.3 8471.9) (8852.2 8689.2) (8852.0 5259.7) (8851.8 2089.4)) (nil (8689.1 2059.4) (6341.4 5346.3) (1513.5 6477.7) (1043.8 6936.1) (5477.5 8066.7) (5996.8 8163.7) (7168.6 8382.5) (7686.9 8479.3) (8859.7 8698.3) (8859.5 5259.7) (8859.3 2089.4)) (nil (6873.3 5242.1) (6425.0 5242.1)) (nil (6873.3 5257.1) (6414.3 5257.1)) (nil (7413.3 8420.5) (7041.2 8351.1)) (nil (6828.9 7670.1) (7420.9 7670.3)) (nil (6828.9 7655.1) (7420.9 7655.3)) (nil (6843.9 7655.1) (6843.9 8312.3)) (nil (6828.9 7655.1) (6828.9 8312.3)) (nil (7411.2 8431.9) (7411.1 8432.2)) (nil (7411.1 8431.9) (7411.1 8432.2)) (nil (7398.3 7655.0) (7399.5 7655.0)) (nil (6893.3 5242.1) (6893.3 6260.2)) (nil (6873.3 5242.1) (6873.3 6260.2)) (nil (1023.6 6952.3) (1025.0 6946.5)) (nil (5807.7 6742.9) (5898.4 6742.9)) (nil (5829.0 6726.7) (5829.0 6759.1)) (T (5839.8 6742.9) (5839.4 6745.7) (5838.3 6748.3) (5836.6 6750.5) (5834.4 6752.2) (5831.8 6753.3) (5829.0 6753.7) (5826.2 6753.3) (5823.6 6752.2) (5821.3 6750.5) (5819.6 6748.3) (5818.6 6745.7) (5818.2 6742.9) (5818.6 6740.1) (5819.6 6737.5) (5821.3 6735.3) (5823.6 6733.5) (5826.2 6732.5) (5829.0 6732.1) (5831.8 6732.5) (5834.4 6733.5) (5836.6 6735.3) (5838.3 6737.5) (5839.4 6740.1) (5839.8 6742.9)) (nil (7981.8 5937.5) (8072.6 5937.5)) (nil (8003.1 5921.4) (8003.1 5953.7)) (T (8013.9 5937.5) (8013.5 5940.3) (8012.5 5942.9) (8010.7 5945.1) (8008.5 5946.9) (8005.9 5947.9) (8003.1 5948.3) (8000.3 5947.9) (7997.7 5946.9) (7995.5 5945.1) (7993.8 5942.9) (7992.7 5940.3) (7992.3 5937.5) (7992.7 5934.7) (7993.8 5932.1) (7995.5 5929.9) (7997.7 5928.2) (8000.3 5927.1) (8003.1 5926.7) (8005.9 5927.1) (8008.5 5928.2) (8010.7 5929.9) (8012.5 5932.1) (8013.5 5934.7) (8013.9 5937.5)) (nil (7406.4 8074.9) (7406.4 8421.4)) (nil (7406.4 7654.4) (7406.4 7924.8)) (nil (7421.3 8059.9) (7421.4 8421.4)) (nil (7421.4 7654.4) (7421.4 7924.8)) (nil (6893.3 6919.4) (6893.3 7655.1)) (nil (6873.3 6919.4) (6873.3 7655.1)) (nil (6893.3 6319.4) (6893.3 6859.4)) (nil (6873.3 6319.4) (6873.3 6859.4)) (nil (8726.2 8673.7) (8728.0 8661.8)) (nil (8554.1 8641.2) (8555.9 8629.3)) (nil (8627.8 8655.6) (8629.5 8643.7)) (T (8859.7 5527.1) (8859.7 5530.1) (8849.7 5530.1) (8849.7 5527.1)) (T (8859.7 5523.1) (8859.7 5530.1) (8861.7 5530.1) (8861.7 5523.1)) (T (8847.7 5523.0) (8847.7 5530.0) (8849.7 5530.1) (8849.7 5523.1)) (T (8859.7 5627.1) (8859.7 5624.1) (8849.7 5624.0) (8849.7 5627.0)) (T (8859.7 5631.1) (8859.7 5624.1) (8861.7 5624.1) (8861.7 5631.1)) (T (8847.7 5631.0) (8847.7 5624.0) (8849.7 5624.0) (8849.7 5631.0)) (T (8861.7 5530.1) (8861.7 5624.1) (8856.7 5624.1) (8856.7 5530.1)) (nil (8861.7 5624.1) (8861.7 5530.1) (8955.7 5530.1)) (nil (8861.7 5624.1) (8886.0 5620.9) (8908.7 5611.5) (8928.1 5596.5) (8943.1 5577.1) (8952.5 5554.4) (8955.7 5530.1)) (T (7615.2 3576.3) (7613.5 3578.7) (7605.3 3572.9) (7607.1 3570.4)) (T (7617.5 3573.0) (7613.5 3578.7) (7615.1 3579.9) (7619.2 3574.2)) (T (7607.8 3566.0) (7603.7 3571.7) (7605.3 3572.9) (7609.4 3567.2)) (T (7556.9 3657.5) (7558.6 3655.0) (7550.5 3649.2) (7548.8 3651.6)) (T (7554.5 3660.7) (7558.6 3655.0) (7560.3 3656.2) (7556.2 3661.9)) (T (7544.8 3653.7) (7548.9 3648.0) (7550.5 3649.2) (7546.4 3654.9)) (T (7615.1 3579.9) (7560.3 3656.2) (7556.2 3653.3) (7611.0 3576.9)) (nil (7560.3 3656.2) (7615.1 3579.9) (7691.4 3634.7)) (nil (7560.3 3656.2) (7581.9 3667.8) (7605.8 3673.4) (7630.3 3672.6) (7653.8 3665.5) (7674.6 3652.6) (7691.4 3634.7))) ((6925.9 8023.5 22.0 "ABDESTHANE") (6925.9 7987.5 16.0 "1,9 m\\U+00B2") (7095.1 8023.6 22.0 "ABDESTHANE") (7095.1 7987.6 16.0 "1,6 m\\U+00B2") (7125.1 7779.9 22.0 "KADIN MESC\\U+0130T") (7125.1 7743.9 16.0 "15,0 m\\U+00B2") (7125.1 8285.5 22.0 "ERKEK MESC\\U+0130T") (7125.1 8249.5 16.0 "15,9 m\\U+00B2")))
   ("BK" "CLD_P2_MIMARI_ZK_V2" ((nil (7626.7 7918.6) (7486.7 7918.6)) (nil (7606.7 8448.2) (7606.7 7938.6)) (nil (7606.7 7938.6) (7486.7 7938.6)) (nil (7486.7 8088.6) (7596.7 8088.6)) (nil (7486.7 8113.6) (7596.7 8113.6)) (nil (7486.7 8138.6) (7596.7 8138.6)) (nil (7486.7 8163.6) (7596.7 8163.6)) (nil (7486.7 8188.6) (7596.7 8188.6)) (nil (7486.7 8213.6) (7596.7 8213.6)) (nil (7486.7 8238.6) (7596.7 8238.6)) (nil (7486.7 8263.6) (7596.7 8263.6)) (nil (7486.7 8288.6) (7596.7 8288.6)) (nil (7486.7 8313.6) (7596.7 8313.6)) (nil (7486.7 8338.6) (7606.7 8338.6)) (nil (7606.7 8063.6) (7486.7 8063.6)) (nil (7486.7 8088.6) (7606.7 8088.6)) (nil (7486.7 8113.6) (7606.7 8113.6)) (nil (7486.7 8138.6) (7606.7 8138.6)) (nil (7486.7 8163.6) (7606.7 8163.6)) (nil (7486.7 8188.6) (7606.7 8188.6)) (nil (7486.7 8213.6) (7606.7 8213.6)) (nil (7486.7 8238.6) (7606.7 8238.6)) (nil (7486.7 8263.6) (7606.7 8263.6)) (nil (7486.7 8288.6) (7606.7 8288.6)) (nil (7486.7 8313.6) (7606.7 8313.6)) (nil (7486.7 8338.6) (7603.7 8338.6)) (nil (7486.7 8063.6) (7486.7 8338.6)) (nil (7486.7 8308.6) (7486.7 8323.6)) (nil (8849.7 2070.6) (8758.3 2070.6) (6411.2 5356.7) (1582.6 6488.3) (1124.0 6935.9) (5544.5 8063.1) (6063.5 8160.0) (7235.3 8378.8) (7753.6 8475.6) (8917.5 8693.0) (8917.3 5263.4) (8917.2 2093.1)) (nil (8849.7 2063.1) (8754.5 2063.1) (6406.7 5350.0) (1578.9 6481.4) (1109.2 6939.9) (5542.9 8070.4) (6062.2 8167.4) (7233.9 8386.2) (7752.3 8483.0) (8925.0 8702.0) (8924.8 5263.4) (8924.7 2093.1)) (nil (6938.7 5245.8) (6490.4 5245.8)) (nil (6938.7 5260.8) (6479.6 5260.8)) (nil (7017.5 8286.0) (7006.6 8345.1)) (nil (7274.7 7878.9) (7274.7 7718.9)) (nil (7284.7 7868.9) (7284.7 7718.9)) (nil (7174.2 7868.8) (7174.2 7718.8)) (nil (7164.2 7868.8) (7164.2 7718.8)) (nil (7122.3 8269.1) (7106.5 8354.8)) (nil (7064.2 7868.8) (7064.2 7718.8)) (nil (7054.2 7868.8) (7054.2 7718.8)) (nil (7426.3 8063.6) (7426.3 7718.9)) (nil (7426.3 8353.6) (7426.3 8063.6)) (nil (7274.7 7878.8) (6954.2 7878.8)) (nil (7426.3 7878.9) (7274.7 7878.9)) (nil (7054.2 7868.8) (6954.2 7868.8)) (nil (7164.2 7868.8) (7064.2 7868.8)) (nil (7264.2 7868.8) (7174.2 7868.8)) (nil (7426.3 7868.9) (7284.7 7868.9)) (nil (6954.2 7718.8) (7426.3 7718.9)) (nil (7168.0 8306.1) (7168.0 8150.4)) (nil (7148.0 8302.4) (7148.0 8170.4)) (nil (6954.2 8279.2) (6954.2 7718.8)) (nil (7168.0 8150.4) (6954.2 8150.4)) (nil (7148.0 8170.4) (6954.2 8170.4)) (nil (7017.5 8286.0) (6955.0 8274.5)) (nil (7148.0 8302.4) (7117.2 8296.8)) (nil (7426.3 8353.6) (7168.0 8306.1)) (nil (6981.3 8344.4) (6894.2 8328.4)) (nil (7478.6 8424.3) (7106.5 8354.8)) (nil (6894.2 7658.8) (7486.3 7659.0)) (nil (6894.2 7658.8) (6894.2 8316.0)) (nil (7476.5 8435.6) (7476.4 8435.9)) (nil (7463.6 7658.8) (7464.9 7658.8)) (nil (6958.7 5245.8) (6958.7 6263.9)) (nil (6938.7 5245.8) (6938.7 6263.9)) (nil (1088.9 6956.1) (1090.4 6950.3)) (nil (5873.1 6746.6) (5963.8 6746.6)) (nil (5894.3 6730.4) (5894.3 6762.8)) (T (5905.1 6746.6) (5904.7 6749.4) (5903.7 6752.0) (5902.0 6754.2) (5899.7 6756.0) (5897.1 6757.0) (5894.3 6757.4) (5891.5 6757.0) (5888.9 6756.0) (5886.7 6754.2) (5885.0 6752.0) (5883.9 6749.4) (5883.5 6746.6) (5883.9 6743.8) (5885.0 6741.2) (5886.7 6739.0) (5888.9 6737.3) (5891.5 6736.2) (5894.3 6735.8) (5897.1 6736.2) (5899.7 6737.3) (5902.0 6739.0) (5903.7 6741.2) (5904.7 6743.8) (5905.1 6746.6)) (nil (8047.2 5941.3) (8137.9 5941.3)) (nil (8068.5 5925.1) (8068.5 5957.4)) (T (8079.3 5941.3) (8078.9 5944.1) (8077.8 5946.6) (8076.1 5948.9) (8073.9 5950.6) (8071.3 5951.7) (8068.5 5952.0) (8065.7 5951.7) (8063.1 5950.6) (8060.9 5948.9) (8059.1 5946.6) (8058.1 5944.1) (8057.7 5941.3) (8058.1 5938.5) (8059.1 5935.9) (8060.9 5933.6) (8063.1 5931.9) (8065.7 5930.9) (8068.5 5930.5) (8071.3 5930.9) (8073.9 5931.9) (8076.1 5933.6) (8077.8 5935.9) (8078.9 5938.5) (8079.3 5941.3)) (nil (7486.7 7658.1) (7486.7 8425.2)) (nil (6986.2 7658.1) (7486.7 7658.1)) (nil (6958.7 6923.1) (6958.7 7613.1)) (nil (6938.7 6923.1) (6938.7 7613.1)) (nil (6958.7 6323.1) (6958.7 6863.1)) (nil (6938.7 6323.1) (6938.7 6863.1)) (nil (8791.6 8677.5) (8793.3 8665.6)) (nil (8619.5 8644.9) (8621.2 8633.1)) (nil (8693.2 8659.4) (8694.9 8647.5)) (nil (8754.5 2063.1) (6406.7 5350.0) (1578.9 6481.4) (1109.2 6939.9) (5542.9 8070.4) (6062.2 8167.4) (7233.9 8386.2) (7752.3 8483.0) (8925.0 8702.0) (8924.8 5263.4) (8924.7 2093.1)) (T (1808.0 7119.5) (1805.1 7118.7) (1807.6 7109.0) (1810.5 7109.8)) (T (1811.9 7120.5) (1805.1 7118.7) (1804.6 7120.7) (1811.4 7122.4)) (T (1814.8 7108.8) (1808.0 7107.1) (1807.6 7109.0) (1814.3 7110.8)) (T (1711.1 7094.8) (1714.0 7095.5) (1716.5 7085.8) (1713.6 7085.1)) (T (1707.2 7093.8) (1714.0 7095.5) (1713.5 7097.4) (1706.7 7095.7)) (T (1710.2 7082.2) (1717.0 7083.9) (1716.5 7085.8) (1709.7 7084.1)) (T (1804.6 7120.7) (1713.5 7097.4) (1714.7 7092.6) (1805.8 7115.8)) (nil (1713.5 7097.4) (1804.6 7120.7) (1781.4 7211.8)) (nil (1713.5 7097.4) (1710.6 7121.8) (1714.1 7146.1) (1723.8 7168.7) (1738.9 7187.9) (1758.6 7202.6) (1781.4 7211.8)) (T (6288.5 8209.7) (6291.4 8210.2) (6293.3 8200.4) (6290.3 8199.8)) (T (6284.5 8208.9) (6291.4 8210.2) (6291.1 8212.2) (6284.2 8210.9)) (T (6286.8 8197.1) (6293.6 8198.4) (6293.3 8200.4) (6286.4 8199.1)) (T (6386.8 8228.0) (6383.8 8227.5) (6385.7 8217.6) (6388.6 8218.2)) (T (6390.7 8228.8) (6383.8 8227.5) (6383.5 8229.4) (6390.3 8230.7)) (T (6392.9 8217.0) (6386.0 8215.7) (6385.7 8217.6) (6392.5 8218.9)) (T (6291.1 8212.2) (6383.5 8229.4) (6384.4 8224.5) (6292.0 8207.3)) (nil (6383.5 8229.4) (6291.1 8212.2) (6273.8 8304.6)) (nil (6383.5 8229.4) (6375.9 8252.8) (6362.5 8273.3) (6344.2 8289.7) (6322.3 8300.8) (6298.3 8305.9) (6273.8 8304.6)) (T (7148.0 8175.2) (7148.0 8178.2) (7168.0 8178.2) (7168.0 8175.2)) (T (7148.0 8171.2) (7148.0 8178.2) (7146.0 8178.2) (7146.0 8171.2)) (T (7170.0 8171.2) (7170.0 8178.2) (7168.0 8178.2) (7168.0 8171.2)) (T (7148.0 8275.2) (7148.0 8272.2) (7168.0 8272.2) (7168.0 8275.2)) (T (7148.0 8279.2) (7148.0 8272.2) (7146.0 8272.2) (7146.0 8279.2)) (T (7170.0 8279.2) (7170.0 8272.2) (7168.0 8272.2) (7168.0 8279.2)) (T (7146.0 8178.2) (7146.0 8272.2) (7151.0 8272.2) (7151.0 8178.2)) (nil (7146.0 8272.2) (7146.0 8178.2) (7052.0 8178.2)) (nil (7146.0 8272.2) (7121.6 8269.0) (7099.0 8259.6) (7079.5 8244.6) (7064.6 8225.2) (7055.2 8202.5) (7052.0 8178.2)) (T (7288.7 7878.9) (7291.7 7878.9) (7291.7 7868.9) (7288.7 7868.9)) (T (7284.7 7878.9) (7291.7 7878.9) (7291.7 7880.9) (7284.7 7880.9)) (T (7284.7 7866.9) (7291.7 7866.9) (7291.7 7868.9) (7284.7 7868.9)) (T (7378.7 7878.9) (7375.7 7878.9) (7375.7 7868.9) (7378.7 7868.9)) (T (7382.7 7878.9) (7375.7 7878.9) (7375.7 7880.9) (7382.7 7880.9)) (T (7382.7 7866.9) (7375.7 7866.9) (7375.7 7868.9) (7382.7 7868.9)) (T (7291.7 7880.9) (7375.7 7880.9) (7375.7 7875.9) (7291.7 7875.9)) (nil (7375.7 7880.9) (7291.7 7880.9) (7291.7 7964.9)) (nil (7291.7 7964.9) (7313.5 7962.0) (7333.7 7953.6) (7351.1 7940.3) (7364.5 7922.9) (7372.9 7902.6) (7375.7 7880.9)) (T (7178.3 7878.8) (7181.3 7878.8) (7181.2 7868.8) (7178.2 7868.8)) (T (7174.3 7878.8) (7181.3 7878.8) (7181.3 7880.8) (7174.3 7880.8)) (T (7174.2 7866.8) (7181.2 7866.8) (7181.2 7868.8) (7174.2 7868.8)) (T (7258.2 7878.8) (7255.2 7878.8) (7255.2 7868.8) (7258.2 7868.8)) (T (7262.2 7878.8) (7255.2 7878.8) (7255.3 7880.8) (7262.3 7880.8)) (T (7262.2 7866.8) (7255.2 7866.8) (7255.2 7868.8) (7262.2 7868.8)) (T (7181.3 7880.8) (7255.3 7880.8) (7255.2 7875.8) (7181.2 7875.8)) (nil (7255.3 7880.8) (7181.3 7880.8) (7181.3 7954.8)) (nil (7181.3 7954.8) (7200.4 7952.3) (7218.3 7944.9) (7233.6 7933.1) (7245.3 7917.8) (7252.7 7900.0) (7255.3 7880.8)) (T (7068.3 7878.8) (7071.3 7878.8) (7071.2 7868.8) (7068.2 7868.8)) (T (7064.3 7878.8) (7071.3 7878.8) (7071.3 7880.8) (7064.3 7880.8)) (T (7064.2 7866.8) (7071.2 7866.8) (7071.2 7868.8) (7064.2 7868.8)) (T (7148.2 7878.8) (7145.2 7878.8) (7145.2 7868.8) (7148.2 7868.8)) (T (7152.2 7878.8) (7145.2 7878.8) (7145.3 7880.8) (7152.3 7880.8)) (T (7152.2 7866.8) (7145.2 7866.8) (7145.2 7868.8) (7152.2 7868.8)) (T (7071.3 7880.8) (7145.3 7880.8) (7145.2 7875.8) (7071.2 7875.8)) (nil (7145.3 7880.8) (7071.3 7880.8) (7071.3 7954.8)) (nil (7071.3 7954.8) (7090.4 7952.3) (7108.3 7944.9) (7123.6 7933.1) (7135.3 7917.8) (7142.7 7900.0) (7145.3 7880.8)) (T (6968.3 7878.8) (6971.3 7878.8) (6971.2 7868.8) (6968.2 7868.8)) (T (6964.3 7878.8) (6971.3 7878.8) (6971.3 7880.8) (6964.3 7880.8)) (T (6964.2 7866.8) (6971.2 7866.8) (6971.2 7868.8) (6964.2 7868.8)) (T (7048.2 7878.8) (7045.2 7878.8) (7045.2 7868.8) (7048.2 7868.8)) (T (7052.2 7878.8) (7045.2 7878.8) (7045.3 7880.8) (7052.3 7880.8)) (T (7052.2 7866.8) (7045.2 7866.8) (7045.2 7868.8) (7052.2 7868.8)) (T (6971.3 7880.8) (7045.3 7880.8) (7045.2 7875.8) (6971.2 7875.8)) (nil (7045.3 7880.8) (6971.3 7880.8) (6971.3 7954.8)) (nil (6971.3 7954.8) (6990.4 7952.3) (7008.3 7944.9) (7023.6 7933.1) (7035.3 7917.8) (7042.7 7900.0) (7045.3 7880.8)) (T (3160.7 6110.7) (3163.6 6110.0) (3165.9 6119.8) (3163.0 6120.5)) (T (3156.8 6111.7) (3163.6 6110.0) (3163.1 6108.1) (3156.3 6109.7)) (T (3159.5 6123.3) (3166.4 6121.7) (3165.9 6119.8) (3159.1 6121.4)) (T (3258.0 6087.7) (3255.1 6088.4) (3257.4 6098.1) (3260.3 6097.4)) (T (3261.9 6086.8) (3255.1 6088.4) (3254.6 6086.4) (3261.4 6084.8)) (T (3264.6 6098.5) (3257.8 6100.1) (3257.4 6098.1) (3264.2 6096.5)) (T (3163.1 6108.1) (3254.6 6086.4) (3255.8 6091.3) (3164.3 6113.0)) (nil (3254.6 6086.4) (3163.1 6108.1) (3141.5 6016.6)) (nil (3254.6 6086.4) (3245.9 6063.5) (3231.5 6043.6) (3212.5 6028.1) (3190.1 6018.1) (3165.9 6014.1) (3141.5 6016.6)) (T (4808.6 7883.2) (4805.7 7882.4) (4808.1 7872.7) (4811.0 7873.5)) (T (4812.5 7884.2) (4805.7 7882.4) (4805.2 7884.4) (4812.0 7886.1)) (T (4815.4 7872.5) (4808.6 7870.8) (4808.1 7872.7) (4814.9 7874.5)) (T (4711.7 7858.5) (4714.6 7859.2) (4717.1 7849.5) (4714.2 7848.8)) (T (4707.8 7857.5) (4714.6 7859.2) (4714.1 7861.1) (4707.3 7859.4)) (T (4710.8 7845.9) (4717.6 7847.6) (4717.1 7849.5) (4710.3 7847.8)) (T (4805.2 7884.4) (4714.1 7861.1) (4715.3 7856.3) (4806.4 7879.5)) (nil (4714.1 7861.1) (4805.2 7884.4) (4782.0 7975.5)) (nil (4714.1 7861.1) (4711.2 7885.5) (4714.7 7909.8) (4724.3 7932.4) (4739.5 7951.6) (4759.2 7966.3) (4782.0 7975.5)) (T (8791.6 8677.5) (8788.6 8676.9) (8790.4 8667.1) (8793.4 8667.6)) (T (8795.5 8678.2) (8788.6 8676.9) (8788.3 8678.9) (8795.2 8680.2)) (T (8797.7 8666.4) (8790.8 8665.1) (8790.4 8667.1) (8797.3 8668.4)) (T (8693.2 8659.4) (8696.2 8659.9) (8698.0 8650.1) (8695.0 8649.5)) (T (8689.3 8658.6) (8696.2 8659.9) (8695.8 8661.9) (8688.9 8660.6)) (T (8691.5 8646.8) (8698.4 8648.1) (8698.0 8650.1) (8691.1 8648.8)) (T (8788.3 8678.9) (8695.8 8661.9) (8696.7 8657.0) (8789.2 8674.0)) (nil (8695.8 8661.9) (8788.3 8678.9) (8771.3 8771.3)) (nil (8695.8 8661.9) (8694.6 8686.4) (8699.7 8710.4) (8710.9 8732.2) (8727.3 8750.4) (8747.9 8763.8) (8771.3 8771.3)) (T (8925.0 5530.8) (8925.0 5533.8) (8915.0 5533.8) (8915.0 5530.8)) (T (8925.0 5526.8) (8925.0 5533.8) (8927.0 5533.8) (8927.0 5526.8)) (T (8913.0 5526.8) (8913.0 5533.8) (8915.0 5533.8) (8915.0 5526.8)) (T (8925.0 5630.8) (8925.0 5627.8) (8915.0 5627.8) (8915.0 5630.8)) (T (8925.0 5634.8) (8925.0 5627.8) (8927.0 5627.8) (8927.0 5634.8)) (T (8913.0 5634.8) (8913.0 5627.8) (8915.0 5627.8) (8915.0 5634.8)) (T (8927.0 5533.8) (8927.0 5627.8) (8922.0 5627.8) (8922.0 5533.8)) (nil (8927.0 5627.8) (8927.0 5533.8) (9021.0 5533.8)) (nil (8927.0 5627.8) (8951.3 5624.6) (8974.0 5615.2) (8993.5 5600.3) (9008.4 5580.8) (9017.8 5558.1) (9021.0 5533.8)) (T (7680.6 3580.0) (7678.8 3582.4) (7670.7 3576.6) (7672.4 3574.2)) (T (7682.9 3576.7) (7678.8 3582.4) (7680.4 3583.6) (7684.5 3577.9)) (T (7673.1 3569.7) (7669.1 3575.4) (7670.7 3576.6) (7674.8 3570.9)) (T (7622.2 3661.2) (7624.0 3658.8) (7615.9 3652.9) (7614.1 3655.4)) (T (7619.9 3664.5) (7624.0 3658.8) (7625.6 3659.9) (7621.5 3665.6)) (T (7610.1 3657.5) (7614.2 3651.8) (7615.9 3652.9) (7611.8 3658.6)) (T (7680.4 3583.6) (7625.6 3659.9) (7621.5 3657.0) (7676.4 3580.7)) (nil (7625.6 3659.9) (7680.4 3583.6) (7756.8 3638.4)) (nil (7625.6 3659.9) (7647.2 3671.5) (7671.1 3677.1) (7695.7 3676.4) (7719.1 3669.3) (7740.0 3656.3) (7756.8 3638.4)) (T (6178.8 5403.4) (6181.7 5402.7) (6184.0 5412.5) (6181.1 5413.1)) (T (6174.9 5404.3) (6181.7 5402.7) (6181.3 5400.8) (6174.5 5402.4)) (T (6177.7 5416.0) (6184.5 5414.4) (6184.0 5412.5) (6177.2 5414.1)) (T (6276.1 5380.4) (6273.2 5381.1) (6275.5 5390.8) (6278.4 5390.1)) (T (6280.0 5379.5) (6273.2 5381.1) (6272.7 5379.1) (6279.6 5377.5)) (T (6282.8 5391.1) (6276.0 5392.7) (6275.5 5390.8) (6282.3 5389.2)) (T (6181.3 5400.8) (6272.7 5379.1) (6273.9 5384.0) (6182.4 5405.6)) (nil (6272.7 5379.1) (6181.3 5400.8) (6159.6 5309.3)) (nil (6272.7 5379.1) (6264.0 5356.2) (6249.7 5336.3) (6230.6 5320.8) (6208.2 5310.7) (6184.0 5306.8) (6159.6 5309.3))) ((7114.2 7814.8 22.0 "BAY WC") (7114.2 7778.8 16.0 "1,5 m\\U+00B2") (7004.2 7814.8 22.0 "BAYAN WC") (7004.2 7778.8 16.0 "1,5 m\\U+00B2") (7224.5 7814.8 22.0 "\\U+00C7\\U+00D6P ODASI") (7224.5 7778.8 16.0 "2,1 m\\U+00B2") (7032.5 8286.4 22.0 "G\\U+00DCV. HOL\\U+00DC") (7032.5 8250.4 16.0 "2,1 m\\U+00B2") (7359.3 7811.9 22.0 "JENARAT\\U+00D6R ODASI") (7359.3 7775.9 16.0 "1,5 m\\U+00B2") (7190.3 8079.4 22.0 "SI\\U+011EINAK") (7190.3 8043.4 16.0 "15,5 m\\U+00B2") (7938.0 5616.7 22.0 "\\U+00DCRET\\U+0130M ALANI") (7938.0 5580.7 16.0 "1.005,3 m\\U+00B2") (4097.1 6829.4 22.0 "\\U+00DCRET\\U+0130M ALANI") (4097.1 6793.4 16.0 "1.009,7 m\\U+00B2")))
   ("T" "CLD-P2-MEK-YAZI" 97243.5 -146058.8 160.0 0 "PARSEL 2 - MEKAN\\U+0130K TES\\U+0130SAT (ISITMA-SO\\U+011EUTMA-HAVALANDIRMA) PROJES\\U+0130")
   ("T" "CLD-P2-MEK-YAZI" 97243.5 -146288.8 50.0 0 "BROSCO \\U+0130THALAT \\U+0130HRACAT VE T\\U+0130CARET ANON\\U+0130M \\U+015E\\U+0130RKET\\U+0130 - YUKARI MAHALLE / KEMALPA\\U+015EA / \\U+0130ZM\\U+0130R")
   ("T" "CLD-P2-MEK-YAZI" 97243.5 -146368.8 38.0 0 "CLD otomatik proje  |  Disiplin 05  |  19.10.2026  |  Paftalar 1/100  |  Katman \\U+00F6neki CLD-P2-MEK-*")
   ("I" "CLD-P2-MEK-ALTLIK" "CLD_P2_MIMARI_ZK_V2" 97243.5 -156785.3 0.0 0.01)
   ("T" "CLD-P2-MEK-TABLO" 107325.2 -146708.8 26.0 0 "LEJANT")
   ("P" "CLD-P2-MEK-TABLO" T 0.0 ((107325.2 -146728.8) (108130.8 -146728.8) (108130.8 -146940.8) (107325.2 -146940.8)))
   ("I" "CLD-P2-MEK-TABLO" "CLD_S_KASET" 107445.2 -146770.8 0.0 0.619)
   ("T" "CLD-P2-MEK-TABLO" 107565.2 -146770.8 20.0 7 "VRF 4 y\\U+00F6nl\\U+00FC kaset tipi i\\U+00E7 \\U+00FCnite (asma tavan)")
   ("I" "CLD-P2-MEK-TABLO" "CLD_S_VRFOUT" 107445.2 -146834.8 0.0 0.4)
   ("T" "CLD-P2-MEK-TABLO" 107565.2 -146834.8 20.0 7 "VRF / multi-split d\\U+0131\\U+015F \\U+00FCnite")
   ("P" "CLD-P2-MEK-SOGUTUCU" nil 0.0 ((107345.2 -146898.8) (107545.2 -146898.8)))
   ("T" "CLD-P2-MEK-TABLO" 107565.2 -146898.8 20.0 7 "So\\U+011Futucu ak\\U+0131\\U+015Fkan boru hatt\\U+0131 (Cu, izoleli)")
   ("P" "CLD-P2-MEK-PAFTA" nil 6.0 ((107175.2 -156805.3) (107175.2 -146558.8)))
   ("P" "CLD-P2-MEK-PAFTA" T 10.0 ((97143.5 -157485.3) (108380.8 -157485.3) (108380.8 -146558.8) (97143.5 -146558.8)))
   ("P" "CLD-P2-MEK-PAFTA" nil 6.0 ((97143.5 -156805.3) (108380.8 -156805.3)))
   ("P" "CLD-P2-MEK-PAFTA" T 6.0 ((105880.8 -157485.3) (108380.8 -157485.3) (108380.8 -156805.3) (105880.8 -156805.3)))
   ("T" "CLD-P2-MEK-YAZI" 105910.8 -156868.5 18.0 0 "\\U+0130\\U+015E\\U+0130N ADI")
   ("T" "CLD-P2-MEK-YAZI" 106500.8 -156868.5 20.0 0 "MEKAN\\U+0130K TES\\U+0130SAT (ISITMA-SO\\U+011EUTMA-HAVALANDIRMA) PROJES\\U+0130")
   ("L" "CLD-P2-MEK-PAFTA" 105880.8 -156902.5 108380.8 -156902.5)
   ("T" "CLD-P2-MEK-YAZI" 105910.8 -156965.6 18.0 0 "YAPI SAH\\U+0130B\\U+0130")
   ("T" "CLD-P2-MEK-YAZI" 106500.8 -156965.6 20.0 0 "BROSCO \\U+0130THALAT \\U+0130HRACAT VE T\\U+0130CARET ANON\\U+0130M \\U+015E\\U+0130RKET\\U+0130")
   ("L" "CLD-P2-MEK-PAFTA" 105880.8 -156999.6 108380.8 -156999.6)
   ("T" "CLD-P2-MEK-YAZI" 105910.8 -157062.7 18.0 0 "ADRES")
   ("T" "CLD-P2-MEK-YAZI" 106500.8 -157062.7 20.0 0 "YUKARI MAHALLE / KEMALPA\\U+015EA / \\U+0130ZM\\U+0130R  -  Ada: ......  Parsel: 2")
   ("L" "CLD-P2-MEK-PAFTA" 105880.8 -157096.7 108380.8 -157096.7)
   ("T" "CLD-P2-MEK-YAZI" 105910.8 -157159.9 18.0 0 "PAFTA ADI")
   ("T" "CLD-P2-MEK-YAZI" 106500.8 -157159.9 20.0 0 "VRF KL\\U+0130MA TES\\U+0130SATI PLANI - ZEM\\U+0130N KAT PLANI")
   ("L" "CLD-P2-MEK-PAFTA" 105880.8 -157193.9 108380.8 -157193.9)
   ("T" "CLD-P2-MEK-YAZI" 105910.8 -157257.0 18.0 0 "\\U+00D6L\\U+00C7EK / TAR\\U+0130H / PAFTA NO")
   ("T" "CLD-P2-MEK-YAZI" 106500.8 -157257.0 20.0 0 "1/100   |   19.10.2026   |   05-01")
   ("L" "CLD-P2-MEK-PAFTA" 105880.8 -157291.0 108380.8 -157291.0)
   ("T" "CLD-P2-MEK-YAZI" 105910.8 -157354.2 18.0 0 "PROJE M\\U+00DCELL\\U+0130F\\U+0130")
   ("T" "CLD-P2-MEK-YAZI" 106500.8 -157354.2 20.0 0 "Makine M\\U+00FChendisi - Ad\\U+0131 Soyad\\U+0131: ..............................")
   ("L" "CLD-P2-MEK-PAFTA" 105880.8 -157388.2 108380.8 -157388.2)
   ("T" "CLD-P2-MEK-YAZI" 105910.8 -157451.3 18.0 0 "ODA S\\U+0130C\\U+0130L / SMM NO")
   ("T" "CLD-P2-MEK-YAZI" 106500.8 -157451.3 20.0 0 "MMO Sicil No: ............   SMM Belge No: ............   \\U+0130mza: ............")
   ("L" "CLD-P2-MEK-PAFTA" 106470.8 -157485.3 106470.8 -156805.3)
   ("T" "CLD-P2-MEK-YAZI" 97243.5 -156945.3 70.0 0 "VRF KL\\U+0130MA TES\\U+0130SATI PLANI")
   ("T" "CLD-P2-MEK-YAZI" 97243.5 -157085.3 40.0 0 "ZEM\\U+0130N KAT PLANI  -  \\U+00D6: 1/100")
   ("T" "CLD-P2-MEK-YAZI" 97243.5 -157185.3 30.0 0 "Parsel 2  |  BROSCO \\U+0130THALAT \\U+0130HRACAT VE T\\U+0130CARET ANON\\U+0130M \\U+015E\\U+0130RKET\\U+0130")
   ("T" "CLD-P2-MEK-YAZI" 97243.5 -157265.3 26.0 0 "CLD - 19.10.2026 - mimari altl\\U+0131k: BROSCO 2 NOLU PARSEL M\\U+0130MAR\\U+0130.dwg")
   ("I" "CLD-P2-MEK-VRF" "CLD_S_VRFOUT" 104320.6 -148199.1 0.0 1.0)
   ("T" "CLD-P2-MEK-YAZI" 104380.6 -148139.1 18.0 0 "Multi-split d\\U+0131\\U+015F \\U+00FCnite 5 kW (sistem 1)")
   ("P" "CLD-P2-MEK-SOGUTUCU" nil 0.0 ((104320.6 -148199.1) (104255.4 -148440.4)))
   ("I" "CLD-P2-MEK-ALTLIK" "CLD_P2_MIMARI_1K_V2" 109480.8 -156785.3 0.0 0.01)
   ("T" "CLD-P2-MEK-TABLO" 119401.7 -146708.8 26.0 0 "LEJANT")
   ("P" "CLD-P2-MEK-TABLO" T 0.0 ((119401.7 -146728.8) (120207.3 -146728.8) (120207.3 -146940.8) (119401.7 -146940.8)))
   ("I" "CLD-P2-MEK-TABLO" "CLD_S_KASET" 119521.7 -146770.8 0.0 0.619)
   ("T" "CLD-P2-MEK-TABLO" 119641.7 -146770.8 20.0 7 "VRF 4 y\\U+00F6nl\\U+00FC kaset tipi i\\U+00E7 \\U+00FCnite (asma tavan)")
   ("I" "CLD-P2-MEK-TABLO" "CLD_S_VRFOUT" 119521.7 -146834.8 0.0 0.4)
   ("T" "CLD-P2-MEK-TABLO" 119641.7 -146834.8 20.0 7 "VRF / multi-split d\\U+0131\\U+015F \\U+00FCnite")
   ("P" "CLD-P2-MEK-SOGUTUCU" nil 0.0 ((119421.7 -146898.8) (119621.7 -146898.8)))
   ("T" "CLD-P2-MEK-TABLO" 119641.7 -146898.8 20.0 7 "So\\U+011Futucu ak\\U+0131\\U+015Fkan boru hatt\\U+0131 (Cu, izoleli)")
   ("P" "CLD-P2-MEK-PAFTA" nil 6.0 ((119251.7 -156805.3) (119251.7 -146558.8)))
   ("P" "CLD-P2-MEK-PAFTA" T 10.0 ((109380.8 -157485.3) (120457.3 -157485.3) (120457.3 -146558.8) (109380.8 -146558.8)))
   ("P" "CLD-P2-MEK-PAFTA" nil 6.0 ((109380.8 -156805.3) (120457.3 -156805.3)))
   ("P" "CLD-P2-MEK-PAFTA" T 6.0 ((117957.3 -157485.3) (120457.3 -157485.3) (120457.3 -156805.3) (117957.3 -156805.3)))
   ("T" "CLD-P2-MEK-YAZI" 117987.3 -156868.5 18.0 0 "\\U+0130\\U+015E\\U+0130N ADI")
   ("T" "CLD-P2-MEK-YAZI" 118577.3 -156868.5 20.0 0 "MEKAN\\U+0130K TES\\U+0130SAT (ISITMA-SO\\U+011EUTMA-HAVALANDIRMA) PROJES\\U+0130")
   ("L" "CLD-P2-MEK-PAFTA" 117957.3 -156902.5 120457.3 -156902.5)
   ("T" "CLD-P2-MEK-YAZI" 117987.3 -156965.6 18.0 0 "YAPI SAH\\U+0130B\\U+0130")
   ("T" "CLD-P2-MEK-YAZI" 118577.3 -156965.6 20.0 0 "BROSCO \\U+0130THALAT \\U+0130HRACAT VE T\\U+0130CARET ANON\\U+0130M \\U+015E\\U+0130RKET\\U+0130")
   ("L" "CLD-P2-MEK-PAFTA" 117957.3 -156999.6 120457.3 -156999.6)
   ("T" "CLD-P2-MEK-YAZI" 117987.3 -157062.7 18.0 0 "ADRES")
   ("T" "CLD-P2-MEK-YAZI" 118577.3 -157062.7 20.0 0 "YUKARI MAHALLE / KEMALPA\\U+015EA / \\U+0130ZM\\U+0130R  -  Ada: ......  Parsel: 2")
   ("L" "CLD-P2-MEK-PAFTA" 117957.3 -157096.7 120457.3 -157096.7)
   ("T" "CLD-P2-MEK-YAZI" 117987.3 -157159.9 18.0 0 "PAFTA ADI")
   ("T" "CLD-P2-MEK-YAZI" 118577.3 -157159.9 20.0 0 "VRF KL\\U+0130MA TES\\U+0130SATI PLANI - 1. KAT PLANI")
   ("L" "CLD-P2-MEK-PAFTA" 117957.3 -157193.9 120457.3 -157193.9)
   ("T" "CLD-P2-MEK-YAZI" 117987.3 -157257.0 18.0 0 "\\U+00D6L\\U+00C7EK / TAR\\U+0130H / PAFTA NO")
   ("T" "CLD-P2-MEK-YAZI" 118577.3 -157257.0 20.0 0 "1/100   |   19.10.2026   |   05-02")
   ("L" "CLD-P2-MEK-PAFTA" 117957.3 -157291.0 120457.3 -157291.0)
   ("T" "CLD-P2-MEK-YAZI" 117987.3 -157354.2 18.0 0 "PROJE M\\U+00DCELL\\U+0130F\\U+0130")
   ("T" "CLD-P2-MEK-YAZI" 118577.3 -157354.2 20.0 0 "Makine M\\U+00FChendisi - Ad\\U+0131 Soyad\\U+0131: ..............................")
   ("L" "CLD-P2-MEK-PAFTA" 117957.3 -157388.2 120457.3 -157388.2)
   ("T" "CLD-P2-MEK-YAZI" 117987.3 -157451.3 18.0 0 "ODA S\\U+0130C\\U+0130L / SMM NO")
   ("T" "CLD-P2-MEK-YAZI" 118577.3 -157451.3 20.0 0 "MMO Sicil No: ............   SMM Belge No: ............   \\U+0130mza: ............")
   ("L" "CLD-P2-MEK-PAFTA" 118547.3 -157485.3 118547.3 -156805.3)
   ("T" "CLD-P2-MEK-YAZI" 109480.8 -156945.3 70.0 0 "VRF KL\\U+0130MA TES\\U+0130SATI PLANI")
   ("T" "CLD-P2-MEK-YAZI" 109480.8 -157085.3 40.0 0 "1. KAT PLANI  -  \\U+00D6: 1/100")
   ("T" "CLD-P2-MEK-YAZI" 109480.8 -157185.3 30.0 0 "Parsel 2  |  BROSCO \\U+0130THALAT \\U+0130HRACAT VE T\\U+0130CARET ANON\\U+0130M \\U+015E\\U+0130RKET\\U+0130")
   ("T" "CLD-P2-MEK-YAZI" 109480.8 -157265.3 26.0 0 "CLD - 19.10.2026 - mimari altl\\U+0131k: BROSCO 2 NOLU PARSEL M\\U+0130MAR\\U+0130.dwg")
   ("I" "CLD-P2-MEK-VRF" "CLD_S_KASET" 116470.7 -148941.3 0.0 1.0)
   ("T" "CLD-P2-MEK-YAZI" 116530.7 -148881.3 18.0 0 "2,2 kW")
   ("I" "CLD-P2-MEK-VRF" "CLD_S_KASET" 116461.6 -148561.7 0.0 1.0)
   ("T" "CLD-P2-MEK-YAZI" 116521.6 -148501.7 18.0 0 "2,2 kW")
   ("P" "CLD-P2-MEK-SOGUTUCU" nil 0.0 ((116427.3 -148444.2) (116427.3 -148941.3) (116470.7 -148941.3)))
   ("P" "CLD-P2-MEK-SOGUTUCU" nil 0.0 ((116427.3 -148444.2) (116427.3 -148561.7) (116461.6 -148561.7)))
   ("I" "CLD-P2-MEK-ALTLIK" "CLD_P2_MIMARI_ZK_V2" 121557.3 -156785.3 0.0 0.01)
   ("T" "CLD-P2-MEK-TABLO" 131639.0 -146708.8 26.0 0 "LEJANT")
   ("P" "CLD-P2-MEK-TABLO" T 0.0 ((131639.0 -146728.8) (132556.2 -146728.8) (132556.2 -147260.8) (131639.0 -147260.8)))
   ("I" "CLD-P2-MEK-TABLO" "CLD_S_HRV" 131759.0 -146770.8 0.0 0.371)
   ("T" "CLD-P2-MEK-TABLO" 131879.0 -146770.8 20.0 7 "Is\\U+0131 geri kazan\\U+0131ml\\U+0131 havaland\\U+0131rma cihaz\\U+0131 (HRV, \\U+03B7 \\U+2265 %75)")
   ("I" "CLD-P2-MEK-TABLO" "CLD_S_MENFEZ" 131759.0 -146834.8 0.0 0.867)
   ("T" "CLD-P2-MEK-TABLO" 131879.0 -146834.8 20.0 7 "Taze hava \\U+00FCfleme anemostad\\U+0131")
   ("I" "CLD-P2-MEK-TABLO" "CLD_S_EMIS" 131759.0 -146898.8 0.0 1.0)
   ("T" "CLD-P2-MEK-TABLO" 131879.0 -146898.8 20.0 7 "Egzoz / emi\\U+015F menfezi")
   ("I" "CLD-P2-MEK-TABLO" "CLD_S_SIGFAN" 131759.0 -146962.8 0.0 0.65)
   ("T" "CLD-P2-MEK-TABLO" 131879.0 -146962.8 20.0 7 "WC egzoz fan\\U+0131 / s\\U+0131\\U+011F\\U+0131nak havaland\\U+0131rma cihaz\\U+0131")
   ("I" "CLD-P2-MEK-TABLO" "CLD_S_CATIFAN" 131759.0 -147026.8 0.0 0.433)
   ("T" "CLD-P2-MEK-TABLO" 131879.0 -147026.8 20.0 7 "\\U+00C7at\\U+0131 tipi aspirat\\U+00F6r (biri frekans invert\\U+00F6rl\\U+00FC)")
   ("I" "CLD-P2-MEK-TABLO" "CLD_S_PANJUR" 131759.0 -147090.8 0.0 0.433)
   ("T" "CLD-P2-MEK-TABLO" 131879.0 -147090.8 20.0 7 "Taze hava panjuru (motorlu damperli)")
   ("P" "CLD-P2-MEK-KANAL-TAZE" nil 0.0 ((131659.0 -147154.8) (131859.0 -147154.8)))
   ("T" "CLD-P2-MEK-TABLO" 131879.0 -147154.8 20.0 7 "Taze hava kanal\\U+0131")
   ("P" "CLD-P2-MEK-KANAL-EGZOZ" nil 0.0 ((131659.0 -147218.8) (131859.0 -147218.8)))
   ("T" "CLD-P2-MEK-TABLO" 131879.0 -147218.8 20.0 7 "Egzoz kanal\\U+0131")
   ("P" "CLD-P2-MEK-PAFTA" nil 6.0 ((131489.0 -156805.3) (131489.0 -146558.8)))
   ("P" "CLD-P2-MEK-PAFTA" T 10.0 ((121457.3 -157485.3) (132806.2 -157485.3) (132806.2 -146558.8) (121457.3 -146558.8)))
   ("P" "CLD-P2-MEK-PAFTA" nil 6.0 ((121457.3 -156805.3) (132806.2 -156805.3)))
   ("P" "CLD-P2-MEK-PAFTA" T 6.0 ((130306.2 -157485.3) (132806.2 -157485.3) (132806.2 -156805.3) (130306.2 -156805.3)))
   ("T" "CLD-P2-MEK-YAZI" 130336.2 -156868.5 18.0 0 "\\U+0130\\U+015E\\U+0130N ADI")
   ("T" "CLD-P2-MEK-YAZI" 130926.2 -156868.5 20.0 0 "MEKAN\\U+0130K TES\\U+0130SAT (ISITMA-SO\\U+011EUTMA-HAVALANDIRMA) PROJES\\U+0130")
   ("L" "CLD-P2-MEK-PAFTA" 130306.2 -156902.5 132806.2 -156902.5)
   ("T" "CLD-P2-MEK-YAZI" 130336.2 -156965.6 18.0 0 "YAPI SAH\\U+0130B\\U+0130")
   ("T" "CLD-P2-MEK-YAZI" 130926.2 -156965.6 20.0 0 "BROSCO \\U+0130THALAT \\U+0130HRACAT VE T\\U+0130CARET ANON\\U+0130M \\U+015E\\U+0130RKET\\U+0130")
   ("L" "CLD-P2-MEK-PAFTA" 130306.2 -156999.6 132806.2 -156999.6)
   ("T" "CLD-P2-MEK-YAZI" 130336.2 -157062.7 18.0 0 "ADRES")))))
(defun cld:ops-p2_mekanik-2 () (cld:play (quote (
   ("T" "CLD-P2-MEK-YAZI" 130926.2 -157062.7 20.0 0 "YUKARI MAHALLE / KEMALPA\\U+015EA / \\U+0130ZM\\U+0130R  -  Ada: ......  Parsel: 2")
   ("L" "CLD-P2-MEK-PAFTA" 130306.2 -157096.7 132806.2 -157096.7)
   ("T" "CLD-P2-MEK-YAZI" 130336.2 -157159.9 18.0 0 "PAFTA ADI")
   ("T" "CLD-P2-MEK-YAZI" 130926.2 -157159.9 20.0 0 "HAVALANDIRMA TES\\U+0130SATI PLANI - ZEM\\U+0130N KAT PLANI")
   ("L" "CLD-P2-MEK-PAFTA" 130306.2 -157193.9 132806.2 -157193.9)
   ("T" "CLD-P2-MEK-YAZI" 130336.2 -157257.0 18.0 0 "\\U+00D6L\\U+00C7EK / TAR\\U+0130H / PAFTA NO")
   ("T" "CLD-P2-MEK-YAZI" 130926.2 -157257.0 20.0 0 "1/100   |   19.10.2026   |   05-03")
   ("L" "CLD-P2-MEK-PAFTA" 130306.2 -157291.0 132806.2 -157291.0)
   ("T" "CLD-P2-MEK-YAZI" 130336.2 -157354.2 18.0 0 "PROJE M\\U+00DCELL\\U+0130F\\U+0130")
   ("T" "CLD-P2-MEK-YAZI" 130926.2 -157354.2 20.0 0 "Makine M\\U+00FChendisi - Ad\\U+0131 Soyad\\U+0131: ..............................")
   ("L" "CLD-P2-MEK-PAFTA" 130306.2 -157388.2 132806.2 -157388.2)
   ("T" "CLD-P2-MEK-YAZI" 130336.2 -157451.3 18.0 0 "ODA S\\U+0130C\\U+0130L / SMM NO")
   ("T" "CLD-P2-MEK-YAZI" 130926.2 -157451.3 20.0 0 "MMO Sicil No: ............   SMM Belge No: ............   \\U+0130mza: ............")
   ("L" "CLD-P2-MEK-PAFTA" 130896.2 -157485.3 130896.2 -156805.3)
   ("T" "CLD-P2-MEK-YAZI" 121557.3 -156945.3 70.0 0 "HAVALANDIRMA TES\\U+0130SATI PLANI")
   ("T" "CLD-P2-MEK-YAZI" 121557.3 -157085.3 40.0 0 "ZEM\\U+0130N KAT PLANI  -  \\U+00D6: 1/100")
   ("T" "CLD-P2-MEK-YAZI" 121557.3 -157185.3 30.0 0 "Parsel 2  |  BROSCO \\U+0130THALAT \\U+0130HRACAT VE T\\U+0130CARET ANON\\U+0130M \\U+015E\\U+0130RKET\\U+0130")
   ("T" "CLD-P2-MEK-YAZI" 121557.3 -157265.3 26.0 0 "CLD - 19.10.2026 - mimari altl\\U+0131k: BROSCO 2 NOLU PARSEL M\\U+0130MAR\\U+0130.dwg")
   ("I" "CLD-P2-MEK-KANAL-EGZOZ" "CLD_S_EMIS" 128671.5 -148992.5 0.0 1.0)
   ("T" "CLD-P2-MEK-YAZI" 128731.5 -148932.5 14.4 0 "50 m\\U+00B3/h")
   ("I" "CLD-P2-MEK-KANAL-EGZOZ" "CLD_S_EMIS" 128561.5 -148992.5 0.0 1.0)
   ("T" "CLD-P2-MEK-YAZI" 128621.5 -148932.5 14.4 0 "50 m\\U+00B3/h")
   ("I" "CLD-P2-MEK-FAN-PANJUR" "CLD_S_SIGFAN" 128747.5 -148727.9 0.0 1.0)
   ("T" "CLD-P2-MEK-YAZI" 128807.5 -148667.9 18.0 0 "S\\U+0131\\U+011F\\U+0131nak havaland\\U+0131rma cihaz\\U+0131 + kum filtresi")
   ("I" "CLD-P2-MEK-FAN-PANJUR" "CLD_S_SIGFAN" 128561.5 -148992.5 0.0 1.0)
   ("T" "CLD-P2-MEK-YAZI" 128621.5 -148932.5 18.0 0 "WC egzoz fan\\U+0131 150 m\\U+00B3/h (\\U+015Faft / \\U+00E7at\\U+0131ya at\\U+0131\\U+015F)")
   ("I" "CLD-P2-MEK-FAN-PANJUR" "CLD_S_CATIFAN" 129868.0 -148757.8 0.0 1.0)
   ("T" "CLD-P2-MEK-YAZI" 129928.0 -148697.8 18.0 0 "12000 m\\U+00B3/h")
   ("I" "CLD-P2-MEK-FAN-PANJUR" "CLD_S_CATIFAN" 129867.9 -150088.9 0.0 1.0)
   ("T" "CLD-P2-MEK-YAZI" 129927.9 -150028.9 18.0 0 "12000 m\\U+00B3/h")
   ("I" "CLD-P2-MEK-FAN-PANJUR" "CLD_S_CATIFAN" 129867.9 -151419.9 0.0 1.0)
   ("T" "CLD-P2-MEK-YAZI" 129927.9 -151359.9 18.0 0 "12000 m\\U+00B3/h")
   ("I" "CLD-P2-MEK-FAN-PANJUR" "CLD_S_PANJUR" 129751.6 -148247.7 4.897 1.0)
   ("T" "CLD-P2-MEK-YAZI" 129811.6 -148187.7 18.0 0 "Taze hava panjuru 1200x800")
   ("I" "CLD-P2-MEK-FAN-PANJUR" "CLD_S_PANJUR" 130454.8 -148729.2 3.1415 1.0)
   ("T" "CLD-P2-MEK-YAZI" 130514.8 -148669.2 18.0 0 "Taze hava panjuru 1200x800")
   ("I" "CLD-P2-MEK-FAN-PANJUR" "CLD_S_PANJUR" 130454.7 -150105.5 3.1415 1.0)
   ("T" "CLD-P2-MEK-YAZI" 130514.7 -150045.5 18.0 0 "Taze hava panjuru 1200x800")
   ("I" "CLD-P2-MEK-FAN-PANJUR" "CLD_S_PANJUR" 130454.6 -151631.8 3.1415 1.0)
   ("T" "CLD-P2-MEK-YAZI" 130514.6 -151571.8 18.0 0 "Taze hava panjuru 1200x800")
   ("I" "CLD-P2-MEK-FAN-PANJUR" "CLD_S_PANJUR" 130454.5 -152858.1 3.1415 1.0)
   ("T" "CLD-P2-MEK-YAZI" 130514.5 -152798.1 18.0 0 "Taze hava panjuru 1200x800")
   ("I" "CLD-P2-MEK-FAN-PANJUR" "CLD_S_PANJUR" 130454.5 -154234.4 3.1415 1.0)
   ("T" "CLD-P2-MEK-YAZI" 130514.5 -154174.4 18.0 0 "Taze hava panjuru 1200x800")
   ("I" "CLD-P2-MEK-FAN-PANJUR" "CLD_S_PANJUR" 129926.3 -154135.3 6.9034 1.0)
   ("T" "CLD-P2-MEK-YAZI" 129986.3 -154075.3 18.0 0 "Taze hava panjuru 1200x800")
   ("I" "CLD-P2-MEK-FAN-PANJUR" "CLD_S_PANJUR" 129023.4 -152871.2 6.9034 1.0)
   ("T" "CLD-P2-MEK-YAZI" 129083.4 -152811.2 18.0 0 "Taze hava panjuru 1200x800")
   ("I" "CLD-P2-MEK-FAN-PANJUR" "CLD_S_PANJUR" 128397.8 -151995.4 6.9034 1.0)
   ("T" "CLD-P2-MEK-YAZI" 128457.8 -151935.4 18.0 0 "Taze hava panjuru 1200x800")
   ("I" "CLD-P2-MEK-FAN-PANJUR" "CLD_S_CATIFAN" 127895.2 -150871.0 0.0 1.0)
   ("T" "CLD-P2-MEK-YAZI" 127955.2 -150811.0 18.0 0 "12000 m\\U+00B3/h")
   ("I" "CLD-P2-MEK-FAN-PANJUR" "CLD_S_CATIFAN" 125677.3 -149753.9 0.0 1.0)
   ("T" "CLD-P2-MEK-YAZI" 125737.3 -149693.9 18.0 0 "12000 m\\U+00B3/h")
   ("I" "CLD-P2-MEK-FAN-PANJUR" "CLD_S_CATIFAN" 127618.9 -149391.3 0.0 1.0)
   ("T" "CLD-P2-MEK-YAZI" 127678.9 -149331.3 18.0 0 "12000 m\\U+00B3/h")
   ("I" "CLD-P2-MEK-FAN-PANJUR" "CLD_S_PANJUR" 123761.2 -149594.7 4.9621 1.0)
   ("T" "CLD-P2-MEK-YAZI" 123821.2 -149534.7 18.0 0 "Taze hava panjuru 1200x800")
   ("I" "CLD-P2-MEK-FAN-PANJUR" "CLD_S_PANJUR" 124603.0 -149380.0 4.9621 1.0)
   ("T" "CLD-P2-MEK-YAZI" 124663.0 -149320.0 18.0 0 "Taze hava panjuru 1200x800")
   ("I" "CLD-P2-MEK-FAN-PANJUR" "CLD_S_PANJUR" 125880.9 -149054.2 4.9621 1.0)
   ("T" "CLD-P2-MEK-YAZI" 125940.9 -148994.2 18.0 0 "Taze hava panjuru 1200x800")
   ("I" "CLD-P2-MEK-FAN-PANJUR" "CLD_S_PANJUR" 127155.8 -148732.5 4.897 1.0)
   ("T" "CLD-P2-MEK-YAZI" 127215.8 -148672.5 18.0 0 "Taze hava panjuru 1200x800")
   ("I" "CLD-P2-MEK-FAN-PANJUR" "CLD_S_PANJUR" 122735.4 -149856.3 4.9621 1.0)
   ("T" "CLD-P2-MEK-YAZI" 122795.4 -149796.3 18.0 0 "Taze hava panjuru 1200x800")
   ("I" "CLD-P2-MEK-FAN-PANJUR" "CLD_S_PANJUR" 127012.1 -151184.0 7.6238 1.0)
   ("T" "CLD-P2-MEK-YAZI" 127072.1 -151124.0 18.0 0 "Taze hava panjuru 1200x800")
   ("I" "CLD-P2-MEK-FAN-PANJUR" "CLD_S_PANJUR" 125728.2 -150883.1 7.6238 1.0)
   ("T" "CLD-P2-MEK-YAZI" 125788.2 -150823.1 18.0 0 "Taze hava panjuru 1200x800")
   ("I" "CLD-P2-MEK-FAN-PANJUR" "CLD_S_PANJUR" 124446.5 -150582.7 7.6238 1.0)
   ("T" "CLD-P2-MEK-YAZI" 124506.5 -150522.7 18.0 0 "Taze hava panjuru 1200x800")
   ("I" "CLD-P2-MEK-FAN-PANJUR" "CLD_S_PANJUR" 123165.7 -150282.9 7.4551 1.0)
   ("T" "CLD-P2-MEK-YAZI" 123225.7 -150222.9 18.0 0 "Taze hava panjuru 1200x800")
   ("P" "CLD-P2-MEK-KANAL-EGZOZ" nil 0.0 ((128561.5 -148992.5) (128671.5 -148992.5)))
   ("I" "CLD-P2-MEK-ALTLIK" "CLD_P2_MIMARI_1K_V2" 133906.2 -156785.3 0.0 0.01)
   ("T" "CLD-P2-MEK-TABLO" 143827.1 -146708.8 26.0 0 "LEJANT")
   ("P" "CLD-P2-MEK-TABLO" T 0.0 ((143827.1 -146728.8) (144744.3 -146728.8) (144744.3 -147260.8) (143827.1 -147260.8)))
   ("I" "CLD-P2-MEK-TABLO" "CLD_S_HRV" 143947.1 -146770.8 0.0 0.371)
   ("T" "CLD-P2-MEK-TABLO" 144067.1 -146770.8 20.0 7 "Is\\U+0131 geri kazan\\U+0131ml\\U+0131 havaland\\U+0131rma cihaz\\U+0131 (HRV, \\U+03B7 \\U+2265 %75)")
   ("I" "CLD-P2-MEK-TABLO" "CLD_S_MENFEZ" 143947.1 -146834.8 0.0 0.867)
   ("T" "CLD-P2-MEK-TABLO" 144067.1 -146834.8 20.0 7 "Taze hava \\U+00FCfleme anemostad\\U+0131")
   ("I" "CLD-P2-MEK-TABLO" "CLD_S_EMIS" 143947.1 -146898.8 0.0 1.0)
   ("T" "CLD-P2-MEK-TABLO" 144067.1 -146898.8 20.0 7 "Egzoz / emi\\U+015F menfezi")
   ("I" "CLD-P2-MEK-TABLO" "CLD_S_SIGFAN" 143947.1 -146962.8 0.0 0.65)
   ("T" "CLD-P2-MEK-TABLO" 144067.1 -146962.8 20.0 7 "WC egzoz fan\\U+0131 / s\\U+0131\\U+011F\\U+0131nak havaland\\U+0131rma cihaz\\U+0131")
   ("I" "CLD-P2-MEK-TABLO" "CLD_S_CATIFAN" 143947.1 -147026.8 0.0 0.433)
   ("T" "CLD-P2-MEK-TABLO" 144067.1 -147026.8 20.0 7 "\\U+00C7at\\U+0131 tipi aspirat\\U+00F6r (biri frekans invert\\U+00F6rl\\U+00FC)")
   ("I" "CLD-P2-MEK-TABLO" "CLD_S_PANJUR" 143947.1 -147090.8 0.0 0.433)
   ("T" "CLD-P2-MEK-TABLO" 144067.1 -147090.8 20.0 7 "Taze hava panjuru (motorlu damperli)")
   ("P" "CLD-P2-MEK-KANAL-TAZE" nil 0.0 ((143847.1 -147154.8) (144047.1 -147154.8)))
   ("T" "CLD-P2-MEK-TABLO" 144067.1 -147154.8 20.0 7 "Taze hava kanal\\U+0131")
   ("P" "CLD-P2-MEK-KANAL-EGZOZ" nil 0.0 ((143847.1 -147218.8) (144047.1 -147218.8)))
   ("T" "CLD-P2-MEK-TABLO" 144067.1 -147218.8 20.0 7 "Egzoz kanal\\U+0131")
   ("P" "CLD-P2-MEK-PAFTA" nil 6.0 ((143677.1 -156805.3) (143677.1 -146558.8)))
   ("P" "CLD-P2-MEK-PAFTA" T 10.0 ((133806.2 -157485.3) (144994.3 -157485.3) (144994.3 -146558.8) (133806.2 -146558.8)))
   ("P" "CLD-P2-MEK-PAFTA" nil 6.0 ((133806.2 -156805.3) (144994.3 -156805.3)))
   ("P" "CLD-P2-MEK-PAFTA" T 6.0 ((142494.3 -157485.3) (144994.3 -157485.3) (144994.3 -156805.3) (142494.3 -156805.3)))
   ("T" "CLD-P2-MEK-YAZI" 142524.3 -156868.5 18.0 0 "\\U+0130\\U+015E\\U+0130N ADI")
   ("T" "CLD-P2-MEK-YAZI" 143114.3 -156868.5 20.0 0 "MEKAN\\U+0130K TES\\U+0130SAT (ISITMA-SO\\U+011EUTMA-HAVALANDIRMA) PROJES\\U+0130")
   ("L" "CLD-P2-MEK-PAFTA" 142494.3 -156902.5 144994.3 -156902.5)
   ("T" "CLD-P2-MEK-YAZI" 142524.3 -156965.6 18.0 0 "YAPI SAH\\U+0130B\\U+0130")
   ("T" "CLD-P2-MEK-YAZI" 143114.3 -156965.6 20.0 0 "BROSCO \\U+0130THALAT \\U+0130HRACAT VE T\\U+0130CARET ANON\\U+0130M \\U+015E\\U+0130RKET\\U+0130")
   ("L" "CLD-P2-MEK-PAFTA" 142494.3 -156999.6 144994.3 -156999.6)
   ("T" "CLD-P2-MEK-YAZI" 142524.3 -157062.7 18.0 0 "ADRES")
   ("T" "CLD-P2-MEK-YAZI" 143114.3 -157062.7 20.0 0 "YUKARI MAHALLE / KEMALPA\\U+015EA / \\U+0130ZM\\U+0130R  -  Ada: ......  Parsel: 2")
   ("L" "CLD-P2-MEK-PAFTA" 142494.3 -157096.7 144994.3 -157096.7)
   ("T" "CLD-P2-MEK-YAZI" 142524.3 -157159.9 18.0 0 "PAFTA ADI")
   ("T" "CLD-P2-MEK-YAZI" 143114.3 -157159.9 20.0 0 "HAVALANDIRMA TES\\U+0130SATI PLANI - 1. KAT PLANI")
   ("L" "CLD-P2-MEK-PAFTA" 142494.3 -157193.9 144994.3 -157193.9)
   ("T" "CLD-P2-MEK-YAZI" 142524.3 -157257.0 18.0 0 "\\U+00D6L\\U+00C7EK / TAR\\U+0130H / PAFTA NO")
   ("T" "CLD-P2-MEK-YAZI" 143114.3 -157257.0 20.0 0 "1/100   |   19.10.2026   |   05-04")
   ("L" "CLD-P2-MEK-PAFTA" 142494.3 -157291.0 144994.3 -157291.0)
   ("T" "CLD-P2-MEK-YAZI" 142524.3 -157354.2 18.0 0 "PROJE M\\U+00DCELL\\U+0130F\\U+0130")
   ("T" "CLD-P2-MEK-YAZI" 143114.3 -157354.2 20.0 0 "Makine M\\U+00FChendisi - Ad\\U+0131 Soyad\\U+0131: ..............................")
   ("L" "CLD-P2-MEK-PAFTA" 142494.3 -157388.2 144994.3 -157388.2)
   ("T" "CLD-P2-MEK-YAZI" 142524.3 -157451.3 18.0 0 "ODA S\\U+0130C\\U+0130L / SMM NO")
   ("T" "CLD-P2-MEK-YAZI" 143114.3 -157451.3 20.0 0 "MMO Sicil No: ............   SMM Belge No: ............   \\U+0130mza: ............")
   ("L" "CLD-P2-MEK-PAFTA" 143084.3 -157485.3 143084.3 -156805.3)
   ("T" "CLD-P2-MEK-YAZI" 133906.2 -156945.3 70.0 0 "HAVALANDIRMA TES\\U+0130SATI PLANI")))))
(defun cld:ops-p2_mekanik-3 () (cld:play (quote (
   ("T" "CLD-P2-MEK-YAZI" 133906.2 -157085.3 40.0 0 "1. KAT PLANI  -  \\U+00D6: 1/100")
   ("T" "CLD-P2-MEK-YAZI" 133906.2 -157185.3 30.0 0 "Parsel 2  |  BROSCO \\U+0130THALAT \\U+0130HRACAT VE T\\U+0130CARET ANON\\U+0130M \\U+015E\\U+0130RKET\\U+0130")
   ("T" "CLD-P2-MEK-YAZI" 133906.2 -157265.3 26.0 0 "CLD - 19.10.2026 - mimari altl\\U+0131k: BROSCO 2 NOLU PARSEL M\\U+0130MAR\\U+0130.dwg")
   ("I" "CLD-P2-MEK-KANAL-EGZOZ" "CLD_S_EMIS" 140832.1 -148783.8 0.0 1.0)
   ("T" "CLD-P2-MEK-YAZI" 140892.1 -148723.8 14.4 0 "100 m\\U+00B3/h")
   ("I" "CLD-P2-MEK-KANAL-EGZOZ" "CLD_S_EMIS" 141001.3 -148783.8 0.0 1.0)
   ("T" "CLD-P2-MEK-YAZI" 141061.3 -148723.8 14.4 0 "100 m\\U+00B3/h")
   ("I" "CLD-P2-MEK-KANAL-TAZE" "CLD_S_MENFEZ" 141258.3 -148978.1 0.0 1.0)
   ("T" "CLD-P2-MEK-YAZI" 141318.3 -148918.1 14.4 0 "145 m\\U+00B3/h")
   ("I" "CLD-P2-MEK-KANAL-EGZOZ" "CLD_S_EMIS" 141118.3 -149078.1 0.0 1.0)
   ("T" "CLD-P2-MEK-YAZI" 141178.3 -149018.1 14.4 0 "145 m\\U+00B3/h")
   ("I" "CLD-P2-MEK-KANAL-TAZE" "CLD_S_MENFEZ" 140966.2 -148978.2 0.0 1.0)
   ("T" "CLD-P2-MEK-YAZI" 141026.2 -148918.2 14.4 0 "145 m\\U+00B3/h")
   ("I" "CLD-P2-MEK-KANAL-EGZOZ" "CLD_S_EMIS" 140826.2 -149078.2 0.0 1.0)
   ("T" "CLD-P2-MEK-YAZI" 140886.2 -149018.2 14.4 0 "145 m\\U+00B3/h")
   ("I" "CLD-P2-MEK-KANAL-TAZE" "CLD_S_MENFEZ" 141053.8 -148506.0 0.0 1.0)
   ("T" "CLD-P2-MEK-YAZI" 141113.8 -148446.0 14.4 0 "159 m\\U+00B3/h")
   ("I" "CLD-P2-MEK-KANAL-EGZOZ" "CLD_S_EMIS" 140913.8 -148606.0 0.0 1.0)
   ("T" "CLD-P2-MEK-YAZI" 140973.8 -148546.0 14.4 0 "159 m\\U+00B3/h")
   ("I" "CLD-P2-MEK-KANAL-TAZE" "CLD_S_MENFEZ" 140957.0 -148511.7 0.0 1.0)
   ("T" "CLD-P2-MEK-YAZI" 141017.0 -148451.7 14.4 0 "159 m\\U+00B3/h")
   ("I" "CLD-P2-MEK-KANAL-EGZOZ" "CLD_S_EMIS" 140817.0 -148611.7 0.0 1.0)
   ("T" "CLD-P2-MEK-YAZI" 140877.0 -148551.7 14.4 0 "159 m\\U+00B3/h")
   ("I" "CLD-P2-MEK-KANAL-TAZE" "CLD_S_HRV" 141031.3 -148521.8 0.0 1.0)
   ("T" "CLD-P2-MEK-YAZI" 141091.3 -148461.8 18.0 0 "HRV 800 m\\U+00B3/h")
   ("I" "CLD-P2-MEK-FAN-PANJUR" "CLD_S_SIGFAN" 140832.1 -148783.8 0.0 1.0)
   ("T" "CLD-P2-MEK-YAZI" 140892.1 -148723.8 18.0 0 "WC egzoz fan\\U+0131 250 m\\U+00B3/h (\\U+015Faft / \\U+00E7at\\U+0131ya at\\U+0131\\U+015F)")
   ("P" "CLD-P2-MEK-KANAL-TAZE" nil 0.0 ((141031.3 -148521.8) (141031.3 -148978.1) (141258.3 -148978.1)))
   ("P" "CLD-P2-MEK-KANAL-EGZOZ" nil 0.0 ((141071.3 -148521.8) (141071.3 -149078.1) (141118.3 -149078.1)))
   ("P" "CLD-P2-MEK-KANAL-TAZE" nil 0.0 ((141031.3 -148521.8) (141031.3 -148978.2) (140966.2 -148978.2)))
   ("P" "CLD-P2-MEK-KANAL-EGZOZ" nil 0.0 ((141071.3 -148521.8) (141071.3 -149078.2) (140826.2 -149078.2)))
   ("P" "CLD-P2-MEK-KANAL-TAZE" nil 0.0 ((141031.3 -148521.8) (141053.8 -148521.8) (141053.8 -148506.0)))
   ("P" "CLD-P2-MEK-KANAL-EGZOZ" nil 0.0 ((141071.3 -148521.8) (140913.8 -148521.8) (140913.8 -148606.0)))
   ("P" "CLD-P2-MEK-KANAL-TAZE" nil 0.0 ((141031.3 -148521.8) (140957.0 -148521.8) (140957.0 -148511.7)))
   ("P" "CLD-P2-MEK-KANAL-EGZOZ" nil 0.0 ((141071.3 -148521.8) (140817.0 -148521.8) (140817.0 -148611.7)))
   ("P" "CLD-P2-MEK-KANAL-EGZOZ" nil 0.0 ((140832.1 -148783.8) (141001.3 -148783.8) (141001.3 -148783.8)))
   ("I" "CLD-P2-MEK-ALTLIK" "CLD_P2_MIMARI_ZK_V2" 146094.3 -156785.3 0.0 0.01)
   ("T" "CLD-P2-MEK-TABLO" 156176.0 -146708.8 26.0 0 "LEJANT")
   ("P" "CLD-P2-MEK-TABLO" T 0.0 ((156176.0 -146728.8) (157006.4 -146728.8) (157006.4 -146812.8) (156176.0 -146812.8)))
   ("I" "CLD-P2-MEK-TABLO" "CLD_S_RADYANT" 156296.0 -146770.8 0.0 0.087)
   ("T" "CLD-P2-MEK-TABLO" 156416.0 -146770.8 20.0 7 "Do\\U+011Falgazl\\U+0131 radyant t\\U+00FCp \\U+0131s\\U+0131t\\U+0131c\\U+0131 15 kW (h=5-6 m)")
   ("P" "CLD-P2-MEK-PAFTA" nil 6.0 ((156026.0 -156805.3) (156026.0 -146558.8)))
   ("P" "CLD-P2-MEK-PAFTA" T 10.0 ((145994.3 -157485.3) (157256.4 -157485.3) (157256.4 -146558.8) (145994.3 -146558.8)))
   ("P" "CLD-P2-MEK-PAFTA" nil 6.0 ((145994.3 -156805.3) (157256.4 -156805.3)))
   ("P" "CLD-P2-MEK-PAFTA" T 6.0 ((154756.4 -157485.3) (157256.4 -157485.3) (157256.4 -156805.3) (154756.4 -156805.3)))
   ("T" "CLD-P2-MEK-YAZI" 154786.4 -156868.5 18.0 0 "\\U+0130\\U+015E\\U+0130N ADI")
   ("T" "CLD-P2-MEK-YAZI" 155376.4 -156868.5 20.0 0 "MEKAN\\U+0130K TES\\U+0130SAT (ISITMA-SO\\U+011EUTMA-HAVALANDIRMA) PROJES\\U+0130")
   ("L" "CLD-P2-MEK-PAFTA" 154756.4 -156902.5 157256.4 -156902.5)
   ("T" "CLD-P2-MEK-YAZI" 154786.4 -156965.6 18.0 0 "YAPI SAH\\U+0130B\\U+0130")
   ("T" "CLD-P2-MEK-YAZI" 155376.4 -156965.6 20.0 0 "BROSCO \\U+0130THALAT \\U+0130HRACAT VE T\\U+0130CARET ANON\\U+0130M \\U+015E\\U+0130RKET\\U+0130")
   ("L" "CLD-P2-MEK-PAFTA" 154756.4 -156999.6 157256.4 -156999.6)
   ("T" "CLD-P2-MEK-YAZI" 154786.4 -157062.7 18.0 0 "ADRES")
   ("T" "CLD-P2-MEK-YAZI" 155376.4 -157062.7 20.0 0 "YUKARI MAHALLE / KEMALPA\\U+015EA / \\U+0130ZM\\U+0130R  -  Ada: ......  Parsel: 2")
   ("L" "CLD-P2-MEK-PAFTA" 154756.4 -157096.7 157256.4 -157096.7)
   ("T" "CLD-P2-MEK-YAZI" 154786.4 -157159.9 18.0 0 "PAFTA ADI")
   ("T" "CLD-P2-MEK-YAZI" 155376.4 -157159.9 20.0 0 "ISITMA (RADYANT) TES\\U+0130SATI PLANI - ZEM\\U+0130N KAT PLANI")
   ("L" "CLD-P2-MEK-PAFTA" 154756.4 -157193.9 157256.4 -157193.9)
   ("T" "CLD-P2-MEK-YAZI" 154786.4 -157257.0 18.0 0 "\\U+00D6L\\U+00C7EK / TAR\\U+0130H / PAFTA NO")
   ("T" "CLD-P2-MEK-YAZI" 155376.4 -157257.0 20.0 0 "1/100   |   19.10.2026   |   05-05")
   ("L" "CLD-P2-MEK-PAFTA" 154756.4 -157291.0 157256.4 -157291.0)
   ("T" "CLD-P2-MEK-YAZI" 154786.4 -157354.2 18.0 0 "PROJE M\\U+00DCELL\\U+0130F\\U+0130")
   ("T" "CLD-P2-MEK-YAZI" 155376.4 -157354.2 20.0 0 "Makine M\\U+00FChendisi - Ad\\U+0131 Soyad\\U+0131: ..............................")
   ("L" "CLD-P2-MEK-PAFTA" 154756.4 -157388.2 157256.4 -157388.2)
   ("T" "CLD-P2-MEK-YAZI" 154786.4 -157451.3 18.0 0 "ODA S\\U+0130C\\U+0130L / SMM NO")
   ("T" "CLD-P2-MEK-YAZI" 155376.4 -157451.3 20.0 0 "MMO Sicil No: ............   SMM Belge No: ............   \\U+0130mza: ............")
   ("L" "CLD-P2-MEK-PAFTA" 155346.4 -157485.3 155346.4 -156805.3)
   ("T" "CLD-P2-MEK-YAZI" 146094.3 -156945.3 70.0 0 "ISITMA (RADYANT) TES\\U+0130SATI PLANI")
   ("T" "CLD-P2-MEK-YAZI" 146094.3 -157085.3 40.0 0 "ZEM\\U+0130N KAT PLANI  -  \\U+00D6: 1/100")
   ("T" "CLD-P2-MEK-YAZI" 146094.3 -157185.3 30.0 0 "Parsel 2  |  BROSCO \\U+0130THALAT \\U+0130HRACAT VE T\\U+0130CARET ANON\\U+0130M \\U+015E\\U+0130RKET\\U+0130")
   ("T" "CLD-P2-MEK-YAZI" 146094.3 -157265.3 26.0 0 "CLD - 19.10.2026 - mimari altl\\U+0131k: BROSCO 2 NOLU PARSEL M\\U+0130MAR\\U+0130.dwg")
   ("I" "CLD-P2-MEK-ISITICI" "CLD_S_RADYANT" 153948.3 -149454.8 1.5707 1.0)
   ("T" "CLD-P2-MEK-YAZI" 154008.3 -149394.8 18.0 0 "Radyant t\\U+00FCp \\U+0131s\\U+0131t\\U+0131c\\U+0131 15 kW")
   ("I" "CLD-P2-MEK-ISITICI" "CLD_S_RADYANT" 153948.2 -150059.9 1.5707 1.0)
   ("T" "CLD-P2-MEK-YAZI" 154008.2 -149999.9 18.0 0 "Radyant t\\U+00FCp \\U+0131s\\U+0131t\\U+0131c\\U+0131 15 kW")
   ("I" "CLD-P2-MEK-ISITICI" "CLD_S_RADYANT" 153948.2 -151269.9 1.5707 1.0)
   ("T" "CLD-P2-MEK-YAZI" 154008.2 -151209.9 18.0 0 "Radyant t\\U+00FCp \\U+0131s\\U+0131t\\U+0131c\\U+0131 15 kW")
   ("I" "CLD-P2-MEK-ISITICI" "CLD_S_RADYANT" 153948.1 -151874.9 1.5707 1.0)
   ("T" "CLD-P2-MEK-YAZI" 154008.1 -151814.9 18.0 0 "Radyant t\\U+00FCp \\U+0131s\\U+0131t\\U+0131c\\U+0131 15 kW")
   ("I" "CLD-P2-MEK-ISITICI" "CLD_S_RADYANT" 154433.7 -148849.8 1.5707 1.0)
   ("T" "CLD-P2-MEK-YAZI" 154493.7 -148789.8 18.0 0 "Radyant t\\U+00FCp \\U+0131s\\U+0131t\\U+0131c\\U+0131 15 kW")
   ("I" "CLD-P2-MEK-ISITICI" "CLD_S_RADYANT" 154433.6 -149454.9 1.5707 1.0)
   ("T" "CLD-P2-MEK-YAZI" 154493.6 -149394.9 18.0 0 "Radyant t\\U+00FCp \\U+0131s\\U+0131t\\U+0131c\\U+0131 15 kW")
   ("I" "CLD-P2-MEK-ISITICI" "CLD_S_RADYANT" 152433.3 -150595.7 -2.957 1.0)
   ("T" "CLD-P2-MEK-YAZI" 152493.3 -150535.7 18.0 0 "Radyant t\\U+00FCp \\U+0131s\\U+0131t\\U+0131c\\U+0131 15 kW")
   ("I" "CLD-P2-MEK-ISITICI" "CLD_S_RADYANT" 150866.6 -150275.8 -2.957 1.0)
   ("T" "CLD-P2-MEK-YAZI" 150926.6 -150215.8 18.0 0 "Radyant t\\U+00FCp \\U+0131s\\U+0131t\\U+0131c\\U+0131 15 kW")
   ("I" "CLD-P2-MEK-ISITICI" "CLD_S_RADYANT" 151594.7 -150139.8 -2.957 1.0)
   ("T" "CLD-P2-MEK-YAZI" 151654.7 -150079.8 18.0 0 "Radyant t\\U+00FCp \\U+0131s\\U+0131t\\U+0131c\\U+0131 15 kW")
   ("I" "CLD-P2-MEK-ISITICI" "CLD_S_RADYANT" 149299.9 -149955.8 -2.957 1.0)
   ("T" "CLD-P2-MEK-YAZI" 149359.9 -149895.8 18.0 0 "Radyant t\\U+00FCp \\U+0131s\\U+0131t\\U+0131c\\U+0131 15 kW")
   ("I" "CLD-P2-MEK-ISITICI" "CLD_S_RADYANT" 150028.0 -149819.8 -2.957 1.0)
   ("T" "CLD-P2-MEK-YAZI" 150088.0 -149759.8 18.0 0 "Radyant t\\U+00FCp \\U+0131s\\U+0131t\\U+0131c\\U+0131 15 kW")
   ("I" "CLD-P2-MEK-ISITICI" "CLD_S_RADYANT" 150756.0 -149683.9 -2.957 1.0)
   ("T" "CLD-P2-MEK-YAZI" 150816.0 -149623.9 18.0 0 "Radyant t\\U+00FCp \\U+0131s\\U+0131t\\U+0131c\\U+0131 15 kW")
   ("T" "CLD-P2-MEK-TABLO" 158356.4 -146808.8 32.5 0 "LEJANT")
   ("P" "CLD-P2-MEK-TABLO" T 0.0 ((158356.4 -146833.8) (159502.9 -146833.8) (159502.9 -147818.8) (158356.4 -147818.8)))
   ("I" "CLD-P2-MEK-TABLO" "CLD_S_KASET" 158506.4 -146886.3 0.0 0.774)
   ("T" "CLD-P2-MEK-TABLO" 158656.4 -146886.3 25.0 7 "VRF 4 y\\U+00F6nl\\U+00FC kaset tipi i\\U+00E7 \\U+00FCnite (asma tavan)")
   ("I" "CLD-P2-MEK-TABLO" "CLD_S_VRFOUT" 158506.4 -146966.3 0.0 0.5)
   ("T" "CLD-P2-MEK-TABLO" 158656.4 -146966.3 25.0 7 "VRF / multi-split d\\U+0131\\U+015F \\U+00FCnite")
   ("P" "CLD-P2-MEK-SOGUTUCU" nil 0.0 ((158381.4 -147046.3) (158631.4 -147046.3)))
   ("T" "CLD-P2-MEK-TABLO" 158656.4 -147046.3 25.0 7 "So\\U+011Futucu ak\\U+0131\\U+015Fkan boru hatt\\U+0131 (Cu, izoleli)")
   ("I" "CLD-P2-MEK-TABLO" "CLD_S_HRV" 158506.4 -147126.3 0.0 0.464)
   ("T" "CLD-P2-MEK-TABLO" 158656.4 -147126.3 25.0 7 "Is\\U+0131 geri kazan\\U+0131ml\\U+0131 havaland\\U+0131rma cihaz\\U+0131 (HRV, \\U+03B7 \\U+2265 %75)")
   ("I" "CLD-P2-MEK-TABLO" "CLD_S_MENFEZ" 158506.4 -147206.3 0.0 1.0)
   ("T" "CLD-P2-MEK-TABLO" 158656.4 -147206.3 25.0 7 "Taze hava \\U+00FCfleme anemostad\\U+0131")
   ("I" "CLD-P2-MEK-TABLO" "CLD_S_EMIS" 158506.4 -147286.3 0.0 1.0)
   ("T" "CLD-P2-MEK-TABLO" 158656.4 -147286.3 25.0 7 "Egzoz / emi\\U+015F menfezi")
   ("I" "CLD-P2-MEK-TABLO" "CLD_S_SIGFAN" 158506.4 -147366.3 0.0 0.812)
   ("T" "CLD-P2-MEK-TABLO" 158656.4 -147366.3 25.0 7 "WC egzoz fan\\U+0131 / s\\U+0131\\U+011F\\U+0131nak havaland\\U+0131rma cihaz\\U+0131")
   ("I" "CLD-P2-MEK-TABLO" "CLD_S_CATIFAN" 158506.4 -147446.3 0.0 0.542)
   ("T" "CLD-P2-MEK-TABLO" 158656.4 -147446.3 25.0 7 "\\U+00C7at\\U+0131 tipi aspirat\\U+00F6r (biri frekans invert\\U+00F6rl\\U+00FC)")
   ("I" "CLD-P2-MEK-TABLO" "CLD_S_PANJUR" 158506.4 -147526.3 0.0 0.542)
   ("T" "CLD-P2-MEK-TABLO" 158656.4 -147526.3 25.0 7 "Taze hava panjuru (motorlu damperli)")
   ("P" "CLD-P2-MEK-KANAL-TAZE" nil 0.0 ((158381.4 -147606.3) (158631.4 -147606.3)))
   ("T" "CLD-P2-MEK-TABLO" 158656.4 -147606.3 25.0 7 "Taze hava kanal\\U+0131")
   ("P" "CLD-P2-MEK-KANAL-EGZOZ" nil 0.0 ((158381.4 -147686.3) (158631.4 -147686.3)))
   ("T" "CLD-P2-MEK-TABLO" 158656.4 -147686.3 25.0 7 "Egzoz kanal\\U+0131")
   ("I" "CLD-P2-MEK-TABLO" "CLD_S_RADYANT" 158506.4 -147766.3 0.0 0.108)
   ("T" "CLD-P2-MEK-TABLO" 158656.4 -147766.3 25.0 7 "Do\\U+011Falgazl\\U+0131 radyant t\\U+00FCp \\U+0131s\\U+0131t\\U+0131c\\U+0131 15 kW (h=5-6 m)")))))
(defun cld:ops-p2_mekanik-4 () (cld:play (quote (
   ("TB" "CLD-P2-MEK-TABLO" 159902.9 -146808.8 25.0 "\\U+0130DAR\\U+0130 B\\U+00D6L\\U+00DCM ISITMA / SO\\U+011EUTMA Y\\U+00DCKLER\\U+0130 VE VRF SE\\U+00C7\\U+0130M\\U+0130 (TS EN 12831 / TS 825)" (("KAT" "MAHAL" "ALAN (m\\U+00B2)" "SO\\U+011EUTMA (W)" "ISITMA (W)" "DI\\U+015E CEPHE (m)" "\\U+0130\\U+00C7 \\U+00DCN\\U+0130TE" "K\\U+0130\\U+015E\\U+0130" "TAZE HAVA (m\\U+00B3/h)") ("1K" "KADIN MESC\\U+0130T" "15,0" "1.946" "859" "0,0" "1 x 2,2 kW" "10" "290") ("1K" "ERKEK MESC\\U+0130T" "15,9" "2.064" "1.410" "5,7" "1 x 2,2 kW" "11" "317") ("" "TOPLAM" "" "4.009" "2.269" "" "4,4 kW" "" "607")))
   ("TB" "CLD-P2-MEK-TABLO" 159902.9 -147383.8 25.0 "MERKEZ\\U+0130 C\\U+0130HAZLAR" (("C\\U+0130HAZ" "KAPAS\\U+0130TE" "A\\U+00C7IKLAMA") ("D\\U+0131\\U+015F \\U+00FCnite sistem 1" "5,0 kW" "i\\U+00E7 \\U+00FCnite toplam\\U+0131 4,4 kW, kombinasyon oran\\U+0131 %88 (hedef %50-130)") ("HRV (1K)" "800 m\\U+00B3/h" "Taze hava 7 l/s\\U+00B7ki\\U+015Fi + 0,7 l/s\\U+00B7m\\U+00B2 (TS EN 16798-1 Kat. II)") ("WC egzoz fan\\U+0131 (ZK)" "150 m\\U+00B3/h" "Islak hacimler 10 hava de\\U+011Fi\\U+015Fimi, cepheye at\\U+0131\\U+015F") ("WC egzoz fan\\U+0131 (1K)" "250 m\\U+00B3/h" "Islak hacimler 10 hava de\\U+011Fi\\U+015Fimi, cepheye at\\U+0131\\U+015F")))
   ("TB" "CLD-P2-MEK-TABLO" 159902.9 -148008.8 25.0 "SO\\U+011EUTUCU AKI\\U+015EKAN YO\\U+011EUNLUK KONTROL\\U+00DC (TS EN 378-1)" (("S\\U+0130STEM" "TAHM\\U+0130N\\U+0130 \\U+015EARJ (kg)" "BORU (m)" "EN K\\U+00DC\\U+00C7\\U+00DCK MAHAL" "HAC\\U+0130M (m\\U+00B3)" "kg/m\\U+00B3" "SINIR" "DURUM") ("Sistem 1" "1,8" "15" "KADIN MESC\\U+0130T" "41,9" "0,04" "0,44 (R410A)" "UYGUN")))
   ("TB" "CLD-P2-MEK-TABLO" 159902.9 -148483.8 25.0 "\\U+00DCRET\\U+0130M HOLLER\\U+0130 HAVALANDIRMA VE ISITMA" (("HOL" "ALAN (m\\U+00B2)" "HAC\\U+0130M (m\\U+00B3)" "YAZ HAVA DE\\U+011E." "EGZOZ (m\\U+00B3/h)" "\\U+00C7ATI FANI" "PANJUR" "v panjur (m/s)" "KI\\U+015E (m\\U+00B3/h)" "ISI KAYBI (kW)" "RADYANT" "KURULU (kW)") ("\\U+00DCRET\\U+0130M ALANI" "1.005,3" "10.063" "3,0 /h" "30.189" "3 x 12.000 m\\U+00B3/h" "9 x 1200x800" "2,1" "7.044" "59,0" "6 x 15 kW" "90") ("\\U+00DCRET\\U+0130M ALANI" "1.009,7" "10.107" "3,0 /h" "30.320" "3 x 12.000 m\\U+00B3/h" "9 x 1200x800" "2,1" "7.075" "58,7" "6 x 15 kW" "90")))
   ("NT" "CLD-P2-MEK-TABLO" 159902.9 -149008.8 25.0 "NOTLAR" ("1- Hesaplar MMO proje haz\\U+0131rlama esaslar\\U+0131 ve TS 825, TS EN 12831, TS EN 16798-1, TS EN 378, TS 3419 e g\\U+00F6redir. D\\U+0131\\U+015F hava: k\\U+0131\\U+015F 0 \\U+00B0C (\\U+0130zmir), yaz 35 \\U+00B0C KT. \\U+0130\\U+00E7: ofis 22 \\U+00B0C, hol 16 \\U+00B0C." "2- U de\\U+011Ferleri: duvar 0,60, \\U+00E7at\\U+0131 0,40, d\\U+00F6\\U+015Feme 0,60, pencere 2,10, sandvi\\U+00E7 panel 0,45 W/m\\U+00B2K." "3- Is\\U+0131 kayb\\U+0131na %10 art\\U+0131r\\U+0131m, 0,5 1/h s\\U+0131zma ve HRV sonras\\U+0131 taze hava \\U+0131s\\U+0131 ihtiyac\\U+0131 eklenmi\\U+015Ftir." "4- Hol \\U+00E7at\\U+0131 fanlar\\U+0131 yaz\\U+0131n 3 1/h \\U+00E7al\\U+0131\\U+015F\\U+0131r; k\\U+0131\\U+015F\\U+0131n yaln\\U+0131z invert\\U+00F6rl\\U+00FC fan d\\U+00FC\\U+015F\\U+00FCk devirde 0,7 1/h (tabloda KI\\U+015E) sa\\U+011Flar, \\U+0131s\\U+0131t\\U+0131c\\U+0131larla kilitlenir; panjurlar motorlu damperlidir." "4a- Panjurlar yaln\\U+0131z hol\\U+00FCn d\\U+0131\\U+015F cephe duvarlar\\U+0131na, serbest kesit h\\U+0131z\\U+0131 \\U+2264 2,2 m/s olacak say\\U+0131 ve boyutta yerle\\U+015Ftirilmi\\U+015Ftir." "4b- Radyant \\U+0131s\\U+0131t\\U+0131c\\U+0131 adedi en az 1 adet / 180 m\\U+00B2 kapsama ile, birim g\\U+00FC\\U+00E7 \\U+0131s\\U+0131 kayb\\U+0131 + %15 ile se\\U+00E7ilmi\\U+015Ftir." "5- VRF boru \\U+00E7aplar\\U+0131 ve so\\U+011Futucu \\U+015Farj\\U+0131 \\U+00FCretici se\\U+00E7im program\\U+0131 ile kesinle\\U+015Ftirilecek; borular kau\\U+00E7uk k\\U+00F6p\\U+00FC\\U+011F\\U+00FC ile izole edilecek, TS EN 378 s\\U+0131n\\U+0131r\\U+0131 a\\U+015F\\U+0131l\\U+0131rsa ka\\U+00E7ak dedekt\\U+00F6r\\U+00FC konacakt\\U+0131r." "6- Radyant \\U+0131s\\U+0131t\\U+0131c\\U+0131lar i\\U+00E7in ayr\\U+0131 do\\U+011Falgaz i\\U+00E7 tesisat projesi (\\U+0130ZM\\U+0130RGAZ / OSB onayl\\U+0131) haz\\U+0131rlanacakt\\U+0131r." "7- S\\U+0131\\U+011F\\U+0131nak havaland\\U+0131rmas\\U+0131 S\\U+0131\\U+011F\\U+0131nak Y\\U+00F6netmeli\\U+011Fi ne g\\U+00F6re el/elektrik tahrikli cihaz + kum filtresi ile yap\\U+0131lacakt\\U+0131r."))
   ("P" "CLD-P2-MEK-PAFTA" T 10.0 ((158156.4 -150771.3) (163556.4 -150771.3) (163556.4 -146508.8) (158156.4 -146508.8)))
   ("P" "CLD-P2-MEK-PAFTA" nil 6.0 ((158156.4 -150021.3) (163556.4 -150021.3)))
   ("T" "CLD-P2-MEK-YAZI" 158256.4 -150211.3 70.0 0 "HESAP TABLOLARI, CETVELLER VE NOTLAR")
   ("T" "CLD-P2-MEK-YAZI" 158256.4 -150371.3 40.0 0 "MEKAN\\U+0130K TES\\U+0130SAT (ISITMA-SO\\U+011EUTMA-HAVALANDIRMA) PROJES\\U+0130  -  \\U+00D6l\\U+00E7eksiz")
   ("P" "CLD-P2-MEK-PAFTA" T 6.0 ((161056.4 -150751.3) (163556.4 -150751.3) (163556.4 -150041.3) (161056.4 -150041.3)))
   ("T" "CLD-P2-MEK-YAZI" 161086.4 -150107.3 18.0 0 "\\U+0130\\U+015E\\U+0130N ADI")
   ("T" "CLD-P2-MEK-YAZI" 161676.4 -150107.3 20.0 0 "MEKAN\\U+0130K TES\\U+0130SAT (ISITMA-SO\\U+011EUTMA-HAVALANDIRMA) PROJES\\U+0130")
   ("L" "CLD-P2-MEK-PAFTA" 161056.4 -150142.8 163556.4 -150142.8)
   ("T" "CLD-P2-MEK-YAZI" 161086.4 -150208.7 18.0 0 "YAPI SAH\\U+0130B\\U+0130")
   ("T" "CLD-P2-MEK-YAZI" 161676.4 -150208.7 20.0 0 "BROSCO \\U+0130THALAT \\U+0130HRACAT VE T\\U+0130CARET ANON\\U+0130M \\U+015E\\U+0130RKET\\U+0130")
   ("L" "CLD-P2-MEK-PAFTA" 161056.4 -150244.2 163556.4 -150244.2)
   ("T" "CLD-P2-MEK-YAZI" 161086.4 -150310.1 18.0 0 "ADRES")
   ("T" "CLD-P2-MEK-YAZI" 161676.4 -150310.1 20.0 0 "YUKARI MAHALLE / KEMALPA\\U+015EA / \\U+0130ZM\\U+0130R  -  Ada: ......  Parsel: 2")
   ("L" "CLD-P2-MEK-PAFTA" 161056.4 -150345.6 163556.4 -150345.6)
   ("T" "CLD-P2-MEK-YAZI" 161086.4 -150411.5 18.0 0 "PAFTA ADI")
   ("T" "CLD-P2-MEK-YAZI" 161676.4 -150411.5 20.0 0 "HESAP TABLOLARI VE NOTLAR")
   ("L" "CLD-P2-MEK-PAFTA" 161056.4 -150447.0 163556.4 -150447.0)
   ("T" "CLD-P2-MEK-YAZI" 161086.4 -150513.0 18.0 0 "\\U+00D6L\\U+00C7EK / TAR\\U+0130H / PAFTA NO")
   ("T" "CLD-P2-MEK-YAZI" 161676.4 -150513.0 20.0 0 "\\U+00D6l\\U+00E7eksiz   |   19.10.2026   |   05-06")
   ("L" "CLD-P2-MEK-PAFTA" 161056.4 -150548.5 163556.4 -150548.5)
   ("T" "CLD-P2-MEK-YAZI" 161086.4 -150614.4 18.0 0 "PROJE M\\U+00DCELL\\U+0130F\\U+0130")
   ("T" "CLD-P2-MEK-YAZI" 161676.4 -150614.4 20.0 0 "Makine M\\U+00FChendisi - Ad\\U+0131 Soyad\\U+0131: ..............................")
   ("L" "CLD-P2-MEK-PAFTA" 161056.4 -150649.9 163556.4 -150649.9)
   ("T" "CLD-P2-MEK-YAZI" 161086.4 -150715.8 18.0 0 "ODA S\\U+0130C\\U+0130L / SMM NO")
   ("T" "CLD-P2-MEK-YAZI" 161676.4 -150715.8 20.0 0 "MMO Sicil No: ............   SMM Belge No: ............   \\U+0130mza: ............")
   ("L" "CLD-P2-MEK-PAFTA" 161646.4 -150751.3 161646.4 -150041.3)))))

(defun c:CLD_P2_MEKANIK ( / *error* olderr)
  (setq *error* cld:err)
  (setq *cld-u* 100.0 *cld-ext* (list 0.0 0.0 1.0))
  (cld:begin "CLD-P2-MEK-*")
  (cld:unlock "CLD-P2-MEK-*")
  (cld:unlock "CLD-MEK-*")
  (cld:clear "CLD-MEK-*")
  (cld:ops-p2_mekanik-layers)
  (cld:clear "CLD-P2-MEK-*")
  (cld:def-symbols)
  (cld:ops-p2_mekanik-1)
  (cld:ops-p2_mekanik-2)
  (cld:ops-p2_mekanik-3)
  (cld:ops-p2_mekanik-4)
  (cld:end "CLD: Parsel 2 - MEKANIK TESISAT (ISITMA-SOGUTMA-HAVALANDIRMA) PROJESI cizildi")
  (princ))

(if (cld:wrong-dwg "2" (list "3" "4" "5"))
  (princ "\nCLD UYARI: Bu dosya PARSEL 2 icindir; acik cizim baska bir parsele ait gorunuyor. Yine de cizmek icin CLD_P2_MEKANIK yazin.")
  (progn (princ "\nCLD: Parsel 2 MEKANIK yukleniyor, cizim olusturuluyor...") (c:CLD_P2_MEKANIK)))
(princ "\nCLD: Yeniden cizmek icin komut: CLD_P2_MEKANIK")
(princ)
