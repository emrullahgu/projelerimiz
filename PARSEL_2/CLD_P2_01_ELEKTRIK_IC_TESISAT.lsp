;;; ==========================================================================
;;; CLD_P2_01_ELEKTRIK_IC_TESISAT.lsp
;;; PARSEL 2 - ELEKTRIK IC TESISAT PROJESI
;;; Isveren : BROSCO ITHALAT IHRACAT VE TICARET ANONIM SIRKETI
;;; Konum   : YUKARI MAHALLE / KEMALPASA / IZMIR
;;; Kaynak  : BROSCO 2 NOLU PARSEL MIMARI.dwg (mimari paftalar)
;;; Kullanim: APPLOAD ile yukleyin -> cizim otomatik olusur.
;;;          Yeniden cizmek icin komut: CLD_P2_ICTESISAT
;;;          Tum ciktilar "CLD-P2-ICT-*" katmanlarindadir; yeniden calistirmada bu katmanlar temizlenir.
;;;          Guvenlik uyarisi gelirse "Bir kez yukle" deyin veya klasoru Secenekler > Dosyalar >
;;;          Guvenilen Konumlar (TRUSTEDPATHS) listesine ekleyin.
;;; Uretici : CLD (Claude) otomatik muhendislik motoru - tum isimler CLD onekli.
;;;   Mimari: 2 kat, 12 mahal, kat kotlari ZK=+0.00, 1K=+3.00, bina yuksekligi 11.21 m
;;;   Elektrik: kurulu 238.6 kW, talep 148.5 kW, trafo 250 kVA, KMP 90 kVAr, jenerator 45 kVA
;;;   Aydinlatma: 107 armatur, 29 priz/cikis, 46 linye, 8 pano
;;;   Topraklama: R=0.97 ohm (birlesik), paratoner LPL I, 27 inis
;;;   Mekanik: VRF 4.4 kW ic unite, dis unite 5.0 kW
;;;   Sihhi: 12 armatur, 1 pis su kolonu, 14 yagmur inisi
;;; ==========================================================================

;;; ==========================================================================
;;; CLD CORE  -  ortak cizim altyapisi (katman, stil, varlik, tablo, oynatici)
;;; Tum isimler CLD onekli. ActiveX (vla-) kullanilmaz: AutoCAD / BricsCAD /
;;; accoreconsole uyumlu saf AutoLISP + entmake.
;;; Mimari paftalar WCS XZ duzleminde (ekstruzyon 0,-1,0) cizildiginden tum
;;; varliklar ayni duzlemde (*cld-ext*) uretilir; koordinatlar pafta (OCS)
;;; koordinatidir.
;;; ==========================================================================

(setq *cld-ver* "1.0")
(if (not *cld-ext*) (setq *cld-ext* '(0.0 0.0 1.0)))
(if (not *cld-u*) (setq *cld-u* 100.0))

;;; ---------------------------------------------------------------- yardimci
(defun cld:m (x) (* x *cld-u*))
(defun cld:3d (p) (list (float (car p)) (float (cadr p)) 0.0))
(defun cld:2d (p) (list (float (car p)) (float (cadr p))))
(defun cld:pxy (p dx dy) (list (+ (car p) dx) (+ (cadr p) dy)))
(defun cld:wcs (p) (trans (cld:3d p) *cld-ext* 0))
(defun cld:top (lay) (/= lay "0"))
(defun cld:x210 (lay) (if (cld:top lay) (list (cons 210 *cld-ext*) '(410 . "Model")) '()))
;; renk / cizgi tipi / kalinlik her zaman acik yazilir: cizimdeki CECOLOR / CELTYPE / CELWEIGHT ne olursa olsun
;; katmandan (ByLayer) gelir; blok icindekiler ByBlock
(defun cld:col (lay)
  (if (= lay "0") '((62 . 0) (6 . "ByBlock") (370 . -2)) '((62 . 256) (6 . "ByLayer") (370 . -1))))
(defun cld:dlen (s / n i)
  ;; gorunen karakter sayisi (\U+XXXX = 1 karakter)
  (setq n 0 i 1)
  (while (<= i (strlen s))
    (if (and (= (substr s i 3) "\\U+") (<= (+ i 6) (strlen s))) (setq i (+ i 7)) (setq i (1+ i)))
    (setq n (1+ n)))
  n)
(defun cld:maxl (l) (if l (apply 'max l) 0))
(defun cld:sum (l) (apply '+ (cons 0 l)))
(defun cld:nth-or (i l def) (if (and l (< i (length l))) (nth i l) def))
(defun cld:range (n / i r) (setq i (1- n)) (while (>= i 0) (setq r (cons i r) i (1- i))) r)

;;; ------------------------------------------------------ tablo kayitlari
(defun cld:ltype (nm desc dash gap / sc)
  (if (not (tblsearch "LTYPE" nm))
    (progn
      (setq sc (max 1e-6 (getvar "LTSCALE")))
      (entmake (list '(0 . "LTYPE") '(100 . "AcDbSymbolTableRecord") '(100 . "AcDbLinetypeTableRecord")
                     (cons 2 nm) '(70 . 0) (cons 3 desc) '(72 . 65) '(73 . 2)
                     (cons 40 (/ (+ dash gap) sc)) (cons 49 (/ dash sc)) '(74 . 0) (cons 49 (- (/ gap sc))) '(74 . 0)))))
  nm)
(defun cld:style ()
  (if (not (tblsearch "STYLE" "CLD_YAZI"))
    (entmake '((0 . "STYLE") (100 . "AcDbSymbolTableRecord") (100 . "AcDbTextStyleTableRecord")
               (2 . "CLD_YAZI") (70 . 0) (40 . 0.0) (41 . 0.85) (50 . 0.0) (71 . 0) (42 . 2.5)
               (3 . "arial.ttf") (4 . ""))))
  "CLD_YAZI")
(defun cld:lay (nm col lt lw / e ed)
  (if (not (tblsearch "LAYER" nm))
    (entmake (list '(0 . "LAYER") '(100 . "AcDbSymbolTableRecord") '(100 . "AcDbLayerTableRecord")
                   (cons 2 nm) '(70 . 0) (cons 62 col)
                   (cons 6 (if (and lt (tblsearch "LTYPE" lt)) lt "Continuous"))
                   (cons 370 lw)))
    (progn
      (setq e (tblobjname "LAYER" nm) ed (entget e))
      (setq ed (subst (cons 70 0) (assoc 70 ed) ed))
      (setq ed (subst (cons 62 col) (assoc 62 ed) ed))
      (if (and lt (tblsearch "LTYPE" lt) (assoc 6 ed)) (setq ed (subst (cons 6 lt) (assoc 6 ed) ed)))
      (if (assoc 370 ed) (setq ed (subst (cons 370 lw) (assoc 370 ed) ed)))
      (entmod ed)))
  nm)

;;; ---------------------------------------------------- varlik olusturucular
;;; lay "0" = blok tanimi icerigi (BYBLOCK renk, blok koordinati)
(defun cld:e-line (a b lay)
  (append (list '(0 . "LINE") (cons 8 lay)) (cld:col lay)
          (if (cld:top lay) (list (cons 10 (cld:wcs a)) (cons 11 (cld:wcs b))) (list (cons 10 (cld:3d a)) (cons 11 (cld:3d b))))
          (cld:x210 lay)))
(defun cld:e-circle (c r lay)
  (append (list '(0 . "CIRCLE") (cons 8 lay)) (cld:col lay) (list (cons 10 (cld:3d c)) (cons 40 r)) (cld:x210 lay)))
(defun cld:e-arc (c r a1 a2 lay)
  (append (list '(0 . "ARC") (cons 8 lay)) (cld:col lay) (list (cons 10 (cld:3d c)) (cons 40 r) (cons 50 a1) (cons 51 a2)) (cld:x210 lay)))
(defun cld:e-pl (pts closed w lay)
  (append (list '(0 . "LWPOLYLINE") '(100 . "AcDbEntity") (cons 8 lay)) (cld:col lay)
          (list '(100 . "AcDbPolyline") (cons 90 (length pts)) (cons 70 (+ (if closed 1 0) (if (cld:top lay) 128 0))) (cons 43 w) '(38 . 0.0))
          (mapcar '(lambda (p) (cons 10 (cld:2d p))) pts)
          (cld:x210 lay)))
(defun cld:e-dot (c r lay)
  (append (list '(0 . "LWPOLYLINE") '(100 . "AcDbEntity") (cons 8 lay)) (cld:col lay)
          (list '(100 . "AcDbPolyline") '(90 . 2) '(70 . 1) (cons 43 r) '(38 . 0.0)
                (cons 10 (list (- (car c) (/ r 2.0)) (cadr c))) '(42 . 1.0)
                (cons 10 (list (+ (car c) (/ r 2.0)) (cadr c))) '(42 . 1.0))
          (cld:x210 lay)))
(defun cld:e-solid (p1 p2 p3 p4 lay)
  (append (list '(0 . "SOLID") (cons 8 lay)) (cld:col lay)
          (list (cons 10 (cld:3d p1)) (cons 11 (cld:3d p2)) (cons 12 (cld:3d p4)) (cons 13 (cld:3d p3)))
          (cld:x210 lay)))
(defun cld:e-text (p h s j lay / ed p3)
  ;; j: 0 sol-taban, 1 orta-taban, 2 sag-taban, 4 orta-orta, 7 sol-orta, 9 sag-orta
  (setq p3 (cld:3d p))
  (setq ed (append (list '(0 . "TEXT") (cons 8 lay)) (cld:col lay)
                   (list (cons 7 (cld:style)) (cons 10 p3) (cons 40 h) (cons 1 s) '(50 . 0.0) '(41 . 0.85))))
  (setq ed (cond ((= j 1) (append ed (list '(72 . 1) (cons 11 p3) '(73 . 0))))
                 ((= j 2) (append ed (list '(72 . 2) (cons 11 p3) '(73 . 0))))
                 ((= j 4) (append ed (list '(72 . 1) (cons 11 p3) '(73 . 2))))
                 ((= j 7) (append ed (list '(72 . 0) (cons 11 p3) '(73 . 2))))
                 ((= j 9) (append ed (list '(72 . 2) (cons 11 p3) '(73 . 2))))
                 (T ed)))
  (append ed (cld:x210 lay)))
(defun cld:e-ins (blk p sc rot lay)
  (append (list '(0 . "INSERT") (cons 8 lay)) (cld:col lay) (list (cons 2 blk) (cons 10 (cld:3d p))
                (cons 41 sc) (cons 42 sc) (cons 43 sc) (cons 50 rot))
          (cld:x210 lay)))
(defun cld:line (a b lay) (entmake (cld:e-line a b lay)))
(defun cld:pl (pts closed w lay) (if (cdr pts) (entmake (cld:e-pl pts closed w lay))))
(defun cld:txt (p h s j lay) (entmake (cld:e-text p h s j lay)))
(defun cld:rect (p1 p2 lay) (cld:pl (list p1 (list (car p2) (cadr p1)) p2 (list (car p1) (cadr p2))) T 0.0 lay))

;;; ------------------------------------------------------------ blok tanimi
(defun cld:defblk (name ents)
  (if (not (tblsearch "BLOCK" name))
    (progn
      (entmake (list '(0 . "BLOCK") (cons 2 name) '(70 . 0) '(10 0.0 0.0 0.0) '(8 . "0")))
      (foreach e ents (entmake e))
      (entmake '((0 . "ENDBLK") (8 . "0")))))
  name)

;;; mimari altlik blogu: plines ((kapali (x y) (x y) ...) ...)  texts ((x y h "yazi") ...)
(defun cld:defblk-bg (name plines texts)
  (if (not (tblsearch "BLOCK" name))
    (progn
      (entmake (list '(0 . "BLOCK") (cons 2 name) '(70 . 0) '(10 0.0 0.0 0.0) '(8 . "0")))
      (foreach p plines (if (cddr p) (entmake (cld:e-pl (cdr p) (car p) 0.0 "0"))))
      (foreach s texts (entmake (cld:e-text (list (car s) (cadr s)) (caddr s) (cadddr s) 4 "0")))
      (entmake '((0 . "ENDBLK") (8 . "0")))))
  name)

;;; ------------------------------------------------------------------ tablo
;;; rows: ((hucre ...) ...)  ilk satir baslik. Sutun genislikleri otomatik.
(defun cld:table (org title rows h lay / ncol widths rh y x w i r cw tw pad s)
  (setq pad (* 0.6 h) rh (* 2.0 h))
  (setq ncol (cld:maxl (mapcar 'length rows)))
  (setq widths (mapcar '(lambda (c)
                          (+ (* 2 pad) (* 0.66 h (cld:maxl (mapcar '(lambda (r) (cld:dlen (cld:nth-or c r ""))) rows)))))
                       (cld:range ncol)))
  (setq tw (cld:sum widths) x (car org) y (cadr org))
  (if (and title (/= title ""))
    (progn
      (cld:rect (list x y) (list (+ x tw) (- y (* 1.5 rh))) lay)
      (cld:txt (list (+ x pad) (- y (* 0.75 rh))) (* 1.3 h) title 7 lay)
      (setq y (- y (* 1.5 rh)))))
  (setq i 0)
  (foreach r rows
    (setq x (car org) cw 0)
    (cld:rect (list x y) (list (+ x tw) (- y rh)) lay)
    (foreach w widths
      (if (> cw 0) (cld:line (list x y) (list x (- y rh)) lay))
      (setq s (cld:nth-or cw r ""))
      (if (/= s "") (cld:txt (list (+ x pad) (- y (* 0.5 rh))) h s 7 lay))
      (setq x (+ x w) cw (1+ cw)))
    (if (= i 0) (cld:pl (list (list (car org) (- y rh)) (list (+ (car org) tw) (- y rh))) nil (* 0.12 h) lay))
    (setq y (- y rh) i (1+ i)))
  (list (- y (* 2.0 h)) tw))
(defun cld:notes (org title lines h lay / y)
  (setq y (cadr org))
  (if (and title (/= title "")) (progn (cld:txt (list (car org) y) (* 1.3 h) title 0 lay) (setq y (- y (* 2.2 h)))))
  (foreach s lines (cld:txt (list (car org) y) h s 0 lay) (setq y (- y (* 1.7 h))))
  (- y h))

;;; ------------------------------------------------------------- oynatici
;;; Hesap motorunun urettigi cizim komutlari:
;;;  ("LY" ad renk cizgitipi kalinlik)        katman
;;;  ("I" lay blok x y aci olcek)             sembol (olcek * *cld-u*)
;;;  ("L" lay x1 y1 x2 y2)                    cizgi
;;;  ("P" lay kapali genislik ((x y) ...))    polyline
;;;  ("C" lay x y r)                          daire
;;;  ("D" lay x y r)                          dolu daire
;;;  ("T" lay x y h hiza "yazi")              yazi
;;;  ("TB" lay x y h "baslik" satirlar)       tablo
;;;  ("NT" lay x y h "baslik" satirlar)       not blogu
(defun cld:op (o / k)
  (setq k (car o))
  (cond ((= k "I") (entmake (cld:e-ins (nth 2 o) (list (nth 3 o) (nth 4 o)) (* (nth 6 o) *cld-u*) (nth 5 o) (nth 1 o))))
        ((= k "L") (cld:line (list (nth 2 o) (nth 3 o)) (list (nth 4 o) (nth 5 o)) (nth 1 o)))
        ((= k "P") (cld:pl (nth 4 o) (nth 2 o) (nth 3 o) (nth 1 o)))
        ((= k "C") (entmake (cld:e-circle (list (nth 2 o) (nth 3 o)) (nth 4 o) (nth 1 o))))
        ((= k "D") (entmake (cld:e-dot (list (nth 2 o) (nth 3 o)) (nth 4 o) (nth 1 o))))
        ((= k "T") (cld:txt (list (nth 2 o) (nth 3 o)) (nth 4 o) (nth 6 o) (nth 5 o) (nth 1 o)))
        ((= k "TB") (cld:table (list (nth 2 o) (nth 3 o)) (nth 5 o) (nth 6 o) (nth 4 o) (nth 1 o)))
        ((= k "NT") (cld:notes (list (nth 2 o) (nth 3 o)) (nth 5 o) (nth 6 o) (nth 4 o) (nth 1 o)))
        ((= k "LY") (cld:lay (nth 1 o) (nth 2 o) (nth 3 o) (nth 4 o)))
        ((= k "BK") (cld:defblk-bg (nth 1 o) (nth 2 o) (nth 3 o)))))
(defun cld:play (ops / r)
  (foreach o ops
    (setq r (vl-catch-all-apply 'cld:op (list o)))
    (cond ((vl-catch-all-error-p r) (setq *cld-bad* (cons (list (car o) (nth 1 o) (vl-catch-all-error-message r)) *cld-bad*)))
          ((and (null r) (or (member (car o) '("I" "L" "C" "D" "T")) (and (= (car o) "P") (cdr (nth 4 o)))))
           (setq *cld-bad* (cons (list (car o) (nth 1 o) (if (= (car o) "I") (nth 2 o) "")) *cld-bad*)))
          (T (setq *cld-n* (1+ *cld-n*))))))

;;; ------------------------------------------------------- calisma ortami
(defun cld:clear (pat / ss i n)
  (setq n 0)
  (if (setq ss (ssget "_X" (list (cons 8 pat))))
    (progn (setq i 0) (while (< i (sslength ss)) (entdel (ssname ss i)) (setq i (1+ i) n (1+ n)))))
  n)
(defun cld:begin (pat)
  (setq *cld-old* (list (getvar "CMDECHO") (getvar "OSMODE")) *cld-n* 0 *cld-bad* nil)
  (setvar "CMDECHO" 0)
  (setvar "OSMODE" 0)
  ;; cizim model alaninda olusur (bir yerlesim sekmesi acik olsa bile)
  (if (= 0 (getvar "TILEMODE")) (vl-catch-all-apply 'setvar (list "TILEMODE" 1)))
  (vl-catch-all-apply 'command-s (list "_.UNDO" "_BEGIN"))
  (cld:style)
  (cld:ltype "CLD_KESIK" "CLD kesik __ __" (cld:m 0.30) (cld:m 0.15))
  (cld:ltype "CLD_NOKTALI" "CLD noktali . . ." (cld:m 0.05) (cld:m 0.10))
  (cld:ltype "CLD_UZUNKESIK" "CLD uzun kesik ____ ____" (cld:m 0.80) (cld:m 0.20)))
;;; disiplin katmanlarinin kilidini kaldir / coz (eski cikti silinebilsin)
(defun cld:unlock (pat / tl ed)
  (setq tl (tblnext "LAYER" T))
  (while tl
    (if (and (wcmatch (cdr (assoc 2 tl)) pat) (/= 0 (logand 5 (cdr (assoc 70 tl)))))
      (progn (setq ed (entget (tblobjname "LAYER" (cdr (assoc 2 tl)))))
             (entmod (subst (cons 70 0) (assoc 70 ed) ed))))
    (setq tl (tblnext "LAYER"))))
(defun cld:restore ()
  (vl-catch-all-apply 'command-s (list "_.UNDO" "_END"))
  (if *cld-old* (progn (setvar "CMDECHO" (car *cld-old*)) (setvar "OSMODE" (cadr *cld-old*))))
  (setq *cld-old* nil))
(defun cld:first5 (l / r i) (setq i 0) (foreach x l (if (< i 5) (setq r (cons x r))) (setq i (1+ i))) (reverse r))
(defun cld:end (msg)
  (cld:restore)
  (princ (strcat "\n" msg " (" (itoa *cld-n*) " varlik/komut)"))
  (if *cld-bad*
    (progn
      (princ (strcat "\nCLD UYARI: " (itoa (length *cld-bad*)) " varlik olusturulamadi, ilkleri:"))
      (foreach b (cld:first5 (reverse *cld-bad*)) (princ (strcat "\n   " (vl-princ-to-string b))))))
  (princ))
;;; acik cizim baska bir parsele mi ait? (dosya adinda baska parselin "<n> NOLU" ifadesi)
(defun cld:wrong-dwg (parcel others / nm bad)
  (setq nm (strcase (getvar "DWGNAME")))
  (foreach o others (if (wcmatch nm (strcat "* " o " NOLU*,BROSCO " o " *,P" o ".DWG")) (setq bad T)))
  (and bad (not (wcmatch nm (strcat "* " parcel " NOLU*,BROSCO " parcel " *,P" parcel ".DWG")))))
(defun cld:err (m)
  (cld:restore)
  (if (not (member m '("Function cancelled" "quit / exit abort"))) (princ (strcat "\nCLD HATA: " m)))
  (princ))


;;; ==========================================================================
;;; CLD SEMBOL KUTUPHANESI - bloklar 1 birim = 1 m tanimlanir, cizime
;;; (olcek x *cld-u*) ile yerlestirilir. Duvar sembollerinde duvar yerel x=0,
;;; sembol +X yonune (mahal icine) bakar.
;;; ==========================================================================

(defun cld:b-box (w h)
  (cld:e-pl (list (list (- (/ w 2)) (- (/ h 2))) (list (/ w 2) (- (/ h 2))) (list (/ w 2) (/ h 2)) (list (- (/ w 2)) (/ h 2))) T 0.0 "0"))
(defun cld:b-wallbox (d w)
  (cld:e-pl (list (list 0.0 (- (/ w 2))) (list d (- (/ w 2))) (list d (/ w 2)) (list 0.0 (/ w 2))) T 0.0 "0"))
(defun cld:b-x (r)
  (list (cld:e-line (list (- r) (- r)) (list r r) "0") (cld:e-line (list (- r) r) (list r (- r)) "0")))
(defun cld:b-txt (p h s) (cld:e-text p h s 4 "0"))

(defun cld:def-symbols ( / r)
  ;; ---------------- AYDINLATMA
  (setq r 0.12)
  (cld:defblk "CLD_S_DL" (append (list (cld:e-circle '(0 0) r "0")) (cld:b-x (* r 0.707))))
  (cld:defblk "CLD_S_DLB" (append (list (cld:e-circle '(0 0) r "0") (cld:e-circle '(0 0) (* r 1.35) "0")) (cld:b-x (* r 0.707))))
  (cld:defblk "CLD_S_HB" (append (list (cld:e-circle '(0 0) 0.30 "0") (cld:e-circle '(0 0) 0.12 "0")) (cld:b-x 0.21)))
  (cld:defblk "CLD_S_PNL" (append (list (cld:b-box 0.6 0.6)) (cld:b-x 0.3)))
  (cld:defblk "CLD_S_ETJ" (list (cld:b-box 1.2 0.2) (cld:e-line '(-0.6 0.0) '(0.6 0.0) "0")
                                (cld:e-line '(-0.5 -0.1) '(-0.5 0.1) "0") (cld:e-line '(0.5 -0.1) '(0.5 0.1) "0")))
  (cld:defblk "CLD_S_PLF" (list (cld:e-circle '(0 0) 0.15 "0") (cld:e-dot '(0 0) 0.07 "0")))
  (cld:defblk "CLD_S_ACIL" (list (cld:b-box 0.32 0.16) (cld:e-solid '(-0.16 -0.08) '(0.16 -0.08) '(0.16 0.08) '(0.16 0.08) "0")))
  (cld:defblk "CLD_S_EXIT" (list (cld:b-box 0.40 0.20) (cld:e-line '(-0.14 0) '(0.12 0) "0") (cld:e-line '(0.12 0) '(0.04 0.06) "0")
                                 (cld:e-line '(0.12 0) '(0.04 -0.06) "0")))
  (cld:defblk "CLD_S_PRJ" (list (cld:e-pl '((-0.15 -0.10) (0.15 -0.10) (0.22 0.12) (-0.22 0.12)) T 0.0 "0") (cld:e-line '(-0.15 0.0) '(0.15 0.0) "0")))
  (cld:defblk "CLD_S_BOLLARD" (list (cld:e-circle '(0 0) 0.12 "0") (cld:e-dot '(0 0) 0.12 "0")))
  ;; ---------------- PRIZ / ANAHTAR (duvar sembolleri)
  (cld:defblk "CLD_S_PRIZ" (list (cld:e-line '(0 0) '(0.06 0) "0") (cld:e-line '(0.06 -0.12) '(0.06 0.12) "0")
                                 (cld:e-arc '(0.06 0) 0.12 (- (/ pi 2)) (/ pi 2) "0") (cld:e-line '(0.20 -0.10) '(0.20 0.10) "0")))
  (cld:defblk "CLD_S_PRIZE" (list (cld:e-line '(0 0) '(0.06 0) "0") (cld:e-line '(0.06 -0.12) '(0.06 0.12) "0")
                                  (cld:e-arc '(0.06 0) 0.12 (- (/ pi 2)) (/ pi 2) "0") (cld:e-dot '(0.11 0) 0.06 "0")
                                  (cld:e-line '(0.20 -0.10) '(0.20 0.10) "0")))
  (cld:defblk "CLD_S_PRIZU" (list (cld:e-line '(0 0) '(0.06 0) "0") (cld:e-line '(0.06 -0.12) '(0.06 0.12) "0")
                                  (cld:e-arc '(0.06 0) 0.12 (- (/ pi 2)) (/ pi 2) "0") (cld:b-txt '(0.11 0) 0.09 "U")))
  (cld:defblk "CLD_S_PRIZ3" (list (cld:e-line '(0 0) '(0.06 0) "0") (cld:e-line '(0.06 -0.14) '(0.06 0.14) "0")
                                  (cld:e-arc '(0.06 0) 0.14 (- (/ pi 2)) (/ pi 2) "0")
                                  (cld:e-line '(0.10 -0.06) '(0.18 -0.06) "0") (cld:e-line '(0.10 0.0) '(0.18 0.0) "0") (cld:e-line '(0.10 0.06) '(0.18 0.06) "0")))
  (cld:defblk "CLD_S_PGRUP" (list (cld:b-box 0.50 0.30) (cld:e-arc '(-0.13 -0.02) 0.08 0.0 pi "0") (cld:e-arc '(0.0 -0.02) 0.08 0.0 pi "0")
                                  (cld:e-arc '(0.13 -0.02) 0.08 0.0 pi "0") (cld:e-line '(-0.25 -0.08) '(0.25 -0.08) "0")))
  (foreach c '(("CLD_S_CK_KLIMA" "K") ("CLD_S_CK_FIRIN" "F") ("CLD_S_CK_BULASIK" "B") ("CLD_S_CK_CAMASIR" "\\U+00C7")
               ("CLD_S_CK_KURUTMA" "KM") ("CLD_S_CK_KOMBI" "KB") ("CLD_S_CK_DAVLUMBAZ" "D") ("CLD_S_CK_POMPA" "P")
               ("CLD_S_CK_ASPIRATOR" "A") ("CLD_S_CK_ASANSOR" "AS") ("CLD_S_CK_SARJ" "EV") ("CLD_S_CK_ISITICI" "IS")
               ("CLD_S_CK_TERMOSIFON" "TS") ("CLD_S_CK_MAKINE" "M"))
    (cld:defblk (car c) (list (cld:b-wallbox 0.24 0.24) (cld:e-solid '(0 -0.12) '(0.08 -0.12) '(0.08 0.12) '(0 0.12) "0")
                              (cld:b-txt '(0.16 0.0) 0.09 (cadr c)))))
  (cld:defblk "CLD_S_ANH1" (list (cld:e-circle '(0.10 0) 0.05 "0") (cld:e-line '(0.135 0.035) '(0.25 0.15) "0") (cld:e-line '(0.25 0.15) '(0.29 0.11) "0")))
  (cld:defblk "CLD_S_ANH2" (list (cld:e-circle '(0.10 0) 0.05 "0") (cld:e-line '(0.135 0.035) '(0.25 0.15) "0") (cld:e-line '(0.25 0.15) '(0.29 0.11) "0")
                                 (cld:e-line '(0.135 -0.035) '(0.25 -0.15) "0") (cld:e-line '(0.25 -0.15) '(0.29 -0.11) "0")))
  (cld:defblk "CLD_S_VAV" (list (cld:e-circle '(0.10 0) 0.05 "0") (cld:e-line '(0.135 0.035) '(0.25 0.15) "0") (cld:e-line '(0.25 0.15) '(0.29 0.11) "0")
                                (cld:e-line '(0.065 -0.035) '(-0.05 -0.15) "0") (cld:e-line '(-0.05 -0.15) '(-0.09 -0.11) "0")))
  (cld:defblk "CLD_S_BUAT" (list (cld:e-circle '(0 0) 0.05 "0")))
  ;; ---------------- PANOLAR
  (cld:defblk "CLD_S_TP" (list (cld:b-wallbox 0.16 0.50) (cld:e-solid '(0 -0.25) '(0.16 -0.25) '(0.16 0.25) '(0 -0.25) "0")))
  (cld:defblk "CLD_S_ADP" (list (cld:b-wallbox 0.30 0.90) (cld:e-solid '(0 -0.45) '(0.30 -0.45) '(0.30 0.45) '(0 0.45) "0")))
  (cld:defblk "CLD_S_KMP" (list (cld:b-wallbox 0.30 0.60) (cld:e-line '(0 -0.30) '(0.30 0.30) "0") (cld:b-txt '(0.15 -0.15) 0.10 "C")))
  (cld:defblk "CLD_S_KOLON" (list (cld:e-circle '(0 0) 0.15 "0") (cld:e-line '(-0.106 -0.106) '(0.106 0.106) "0")
                                  (cld:e-line '(0.106 0.106) '(0.02 0.106) "0") (cld:e-line '(0.106 0.106) '(0.106 0.02) "0")))
  (cld:defblk "CLD_S_OAP" (list (cld:b-wallbox 0.20 0.60) (cld:e-solid '(0 -0.30) '(0.20 -0.30) '(0.20 0.0) '(0 0.0) "0")))
  (cld:defblk "CLD_S_TRAFO" (list (cld:b-box 6.0 5.0) (cld:e-circle '(-0.45 0) 0.8 "0") (cld:e-circle '(0.45 0) 0.8 "0")))
  (cld:defblk "CLD_S_JEN" (list (cld:b-box 4.0 1.6) (cld:e-circle '(-1.2 0) 0.55 "0") (cld:b-txt '(-1.2 0) 0.5 "G")))
  ;; ---------------- TOPRAKLAMA / PARATONER
  (cld:defblk "CLD_S_TOP_FILIZ" (list (cld:e-circle '(0 0) 0.15 "0") (cld:e-dot '(0 0) 0.12 "0")))
  (cld:defblk "CLD_S_TOP_EPB" (list (cld:b-box 0.60 0.16) (cld:e-solid '(-0.30 -0.08) '(0.30 -0.08) '(0.30 0.08) '(-0.30 0.08) "0")
                                    (cld:e-line '(-0.2 -0.08) '(-0.2 -0.25) "0") (cld:e-line '(0 -0.08) '(0 -0.25) "0") (cld:e-line '(0.2 -0.08) '(0.2 -0.25) "0")))
  (cld:defblk "CLD_S_TOP_YEB" (list (cld:b-wallbox 0.10 0.30) (cld:e-solid '(0 -0.15) '(0.10 -0.15) '(0.10 0.15) '(0 0.15) "0")))
  (cld:defblk "CLD_S_TOP_KAZIK" (list (cld:e-line '(0 0.20) '(0 0) "0") (cld:e-line '(-0.15 0) '(0.15 0) "0")
                                      (cld:e-line '(-0.10 -0.05) '(0.10 -0.05) "0") (cld:e-line '(-0.05 -0.10) '(0.05 -0.10) "0")
                                      (cld:e-circle '(0 0.05) 0.25 "0")))
  (cld:defblk "CLD_S_TOP_OLCU" (append (list (cld:b-box 0.30 0.30)) (cld:b-x 0.15)))
  (cld:defblk "CLD_S_PAR_UC" (list (cld:e-circle '(0 0) 0.20 "0") (cld:e-solid '(-0.12 -0.08) '(0.12 -0.08) '(0.0 0.14) '(0.0 0.14) "0")))
  (cld:defblk "CLD_S_PAR_INIS" (list (cld:e-circle '(0 0) 0.15 "0") (cld:e-dot '(0 0) 0.08 "0")
                                     (cld:e-line '(0.0 -0.15) '(0.0 -0.40) "0") (cld:e-line '(-0.08 -0.30) '(0.0 -0.40) "0") (cld:e-line '(0.08 -0.30) '(0.0 -0.40) "0")))
  (cld:defblk "CLD_S_PAR_KLEMENS" (list (cld:b-box 0.25 0.25) (cld:e-solid '(-0.125 -0.125) '(0.125 -0.125) '(0.125 0.125) '(-0.125 -0.125) "0")))
  ;; ---------------- MEKANIK
  (cld:defblk "CLD_S_KASET" (append (list (cld:b-box 0.84 0.84) (cld:b-box 0.56 0.56)) (cld:b-x 0.28)))
  (cld:defblk "CLD_S_VRFOUT" (list (cld:b-box 1.30 0.75) (cld:e-circle '(-0.3 0) 0.28 "0") (cld:e-circle '(0.3 0) 0.28 "0")))
  (cld:defblk "CLD_S_HRV" (list (cld:b-box 1.40 0.80) (cld:e-line '(-0.7 -0.4) '(0.7 0.4) "0") (cld:e-line '(-0.7 0.4) '(0.7 -0.4) "0") (cld:b-txt '(0 0.25) 0.15 "HRV")))
  (cld:defblk "CLD_S_MENFEZ" (append (list (cld:b-box 0.60 0.60) (cld:b-box 0.30 0.30)) (cld:b-x 0.30)))
  (cld:defblk "CLD_S_EMIS" (list (cld:b-box 0.40 0.40) (cld:e-line '(-0.2 -0.1) '(0.2 -0.1) "0") (cld:e-line '(-0.2 0.0) '(0.2 0.0) "0") (cld:e-line '(-0.2 0.1) '(0.2 0.1) "0")))
  (cld:defblk "CLD_S_CATIFAN" (list (cld:e-circle '(0 0) 0.60 "0") (cld:e-circle '(0 0) 0.15 "0") (cld:e-line '(0 0) '(0.5 0.25) "0")
                                    (cld:e-line '(0 0) '(-0.5 0.25) "0") (cld:e-line '(0 0) '(0 -0.55) "0")))
  (cld:defblk "CLD_S_PANJUR" (list (cld:b-wallbox 0.20 1.20) (cld:e-line '(0 -0.4) '(0.2 -0.3) "0") (cld:e-line '(0 0.0) '(0.2 0.1) "0") (cld:e-line '(0 0.4) '(0.2 0.5) "0")))
  (cld:defblk "CLD_S_RADYANT" (list (cld:e-pl '((-3.0 -0.15) (3.0 -0.15) (3.0 0.15) (-3.0 0.15)) T 0.0 "0") (cld:e-line '(-3.0 0) '(2.6 0) "0") (cld:b-box 0.6 0.4)))
  (cld:defblk "CLD_S_SIGFAN" (list (cld:b-box 0.80 0.60) (cld:e-circle '(0 0) 0.22 "0") (cld:b-txt '(0 -0.2) 0.10 "S")))
  ;; ---------------- SIHHI TESISAT
  (cld:defblk "CLD_S_PK" (append (list (cld:e-circle '(0 0) 0.10 "0")) (cld:b-x 0.07)))
  (cld:defblk "CLD_S_TSK" (list (cld:e-circle '(0 0) 0.08 "0") (cld:e-dot '(0 0) 0.05 "0")))
  (cld:defblk "CLD_S_YK" (list (cld:e-circle '(0 0) 0.10 "0") (cld:e-circle '(0 0) 0.05 "0")))
  (cld:defblk "CLD_S_YS" (list (cld:b-box 0.18 0.18) (cld:e-circle '(0 0) 0.06 "0") (cld:e-line '(-0.06 0) '(0.06 0) "0")))
  (cld:defblk "CLD_S_SUSAYAC" (list (cld:e-circle '(0 0) 0.12 "0") (cld:e-line '(-0.12 0) '(0.12 0) "0") (cld:b-txt '(0 0.05) 0.06 "m3")))
  (cld:defblk "CLD_S_ROGAR" (list (cld:b-box 0.60 0.60) (cld:e-circle '(0 0) 0.22 "0")))
  (cld:defblk "CLD_S_DEPO" (append (list (cld:b-box 1.20 0.80)) (list (cld:e-line '(-0.6 -0.4) '(0.6 0.4) "0") (cld:e-line '(-0.6 0.4) '(0.6 -0.4) "0"))))
  (cld:defblk "CLD_S_KLOZET" (list (cld:e-pl '((-0.18 0.30) (0.18 0.30) (0.18 0.12) (-0.18 0.12)) T 0.0 "0")
                                   (cld:e-circle '(0 -0.08) 0.18 "0")))
  (cld:defblk "CLD_S_LAVABO" (list (cld:b-box 0.50 0.40) (cld:e-circle '(0 -0.03) 0.13 "0")))
  (cld:defblk "CLD_S_ABDEST" (list (cld:b-box 0.40 0.30) (cld:e-circle '(0 0.05) 0.05 "0") (cld:e-line '(0 0.05) '(0 -0.12) "0")))
  (cld:defblk "CLD_S_YD" (list (cld:b-wallbox 0.25 0.80) (cld:e-solid '(0 -0.40) '(0.25 -0.40) '(0.25 -0.10) '(0 -0.10) "0")
                              (cld:b-txt '(0.125 0.15) 0.12 "YD")))
  (cld:defblk "CLD_S_DUS" (append (list (cld:b-box 0.90 0.90) (cld:e-circle '(0 0) 0.06 "0")) (cld:b-x 0.45)))
  T)


(setq *cld-u* 100.0)
(setq *cld-ext* (list 0.0 0.0 1.0))

(defun cld:ops-p2_elektrik_ic_tesisat-layers () (cld:play (quote (("LY" "CLD-P2-ICT-YAZI" 7 nil -3) ("LY" "CLD-P2-ICT-PAFTA" 7 nil 50) ("LY" "CLD-P2-ICT-ALTLIK" 8 nil 13) ("LY" "CLD-P2-ICT-TABLO" 7 nil -3) ("LY" "CLD-P2-ICT-AYDINLATMA" 2 nil -3) ("LY" "CLD-P2-ICT-ACIL" 1 nil -3) ("LY" "CLD-P2-ICT-PRIZ" 4 nil -3) ("LY" "CLD-P2-ICT-OZEL-CIKIS" 6 nil -3) ("LY" "CLD-P2-ICT-ANAHTAR" 3 nil -3) ("LY" "CLD-P2-ICT-LINYE-AYD" 2 "CLD_KESIK" 13) ("LY" "CLD-P2-ICT-LINYE-PRIZ" 4 "CLD_UZUNKESIK" 13) ("LY" "CLD-P2-ICT-PANO" 1 nil 50)))))
(defun cld:ops-p2_elektrik_ic_tesisat-1 () (cld:play (quote (
   ("BK" "CLD_P2_MIMARI_1K_V2" ((nil (7250.3 7995.7) (7341.0 7995.7)) (nil (7271.6 7979.5) (7271.6 8011.8)) (T (7282.4 7995.7) (7282.0 7998.5) (7280.9 8001.1) (7279.2 8003.3) (7277.0 8005.0) (7274.4 8006.1) (7271.6 8006.4) (7268.8 8006.1) (7266.2 8005.0) (7264.0 8003.3) (7262.2 8001.1) (7261.2 7998.5) (7260.8 7995.7) (7261.2 7992.9) (7262.2 7990.3) (7264.0 7988.0) (7266.2 7986.3) (7268.8 7985.2) (7271.6 7984.9) (7274.4 7985.2) (7277.0 7986.3) (7279.2 7988.0) (7280.9 7990.3) (7282.0 7992.9) (7282.4 7995.7)) (nil (7176.3 8201.6) (7267.0 8201.6)) (nil (7197.5 8185.4) (7197.5 8217.8)) (T (7208.3 8201.6) (7207.9 8204.4) (7206.9 8207.0) (7205.2 8209.2) (7202.9 8210.9) (7200.3 8212.0) (7197.5 8212.4) (7194.7 8212.0) (7192.1 8210.9) (7189.9 8209.2) (7188.2 8207.0) (7187.1 8204.4) (7186.7 8201.6) (7187.1 8198.8) (7188.2 8196.2) (7189.9 8193.9) (7192.1 8192.2) (7194.7 8191.2) (7197.5 8190.8) (7200.3 8191.2) (7202.9 8192.2) (7205.2 8193.9) (7206.9 8196.2) (7207.9 8198.8) (7208.3 8201.6)) (nil (7329.4 7939.8) (7325.4 7939.8)) (nil (7329.4 7924.8) (7329.4 7939.8)) (nil (7239.4 7924.8) (7239.4 7939.8)) (nil (7322.6 7845.4) (7326.6 7845.4)) (nil (7322.6 7924.8) (7322.6 7845.4)) (nil (7326.6 7845.4) (7326.6 7924.8)) (nil (7325.4 7928.8) (7325.4 7939.8)) (nil (7326.6 7928.8) (7325.4 7928.8)) (nil (7326.6 7924.8) (7326.6 7928.8)) (nil (7329.4 7924.8) (7326.6 7924.8)) (nil (7329.4 7939.8) (7329.4 7924.8)) (nil (7239.4 7939.8) (7243.4 7939.8)) (nil (7239.4 7924.8) (7239.4 7939.8)) (nil (7242.2 7924.8) (7239.4 7924.8)) (nil (7242.2 7928.8) (7242.2 7924.8)) (nil (7243.4 7928.8) (7242.2 7928.8)) (nil (7243.4 7939.8) (7243.4 7928.8)) (nil (7242.2 7924.8) (7252.8 7896.0) (7271.8 7871.7) (7297.1 7854.3) (7326.6 7845.4)) (nil (7239.4 7924.8) (7239.4 7939.8)) (nil (7329.4 7924.8) (7329.4 7939.8)) (nil (7329.4 7939.8) (7329.4 7924.8)) (nil (7329.4 8059.8) (7325.4 8059.8)) (nil (7329.4 8074.8) (7329.4 8059.8)) (nil (7239.4 8074.8) (7239.4 8059.8)) (nil (7322.6 8154.2) (7326.6 8154.2)) (nil (7322.6 8074.8) (7322.6 8154.2)) (nil (7326.6 8154.2) (7326.6 8074.8)) (nil (7325.4 8070.8) (7325.4 8059.8)) (nil (7326.6 8070.8) (7325.4 8070.8)) (nil (7326.6 8074.8) (7326.6 8070.8)) (nil (7329.4 8074.8) (7326.6 8074.8)) (nil (7329.4 8059.8) (7329.4 8074.8)) (nil (7239.4 8059.8) (7243.4 8059.8)) (nil (7239.4 8074.8) (7239.4 8059.8)) (nil (7242.2 8074.8) (7239.4 8074.8)) (nil (7242.2 8070.8) (7242.2 8074.8)) (nil (7243.4 8070.8) (7242.2 8070.8)) (nil (7243.4 8059.8) (7243.4 8070.8)) (nil (7326.6 8154.2) (7297.1 8145.4) (7271.8 8128.0) (7252.8 8103.7) (7242.2 8074.8)) (nil (7239.4 8074.8) (7239.4 8059.8)) (nil (7329.4 8074.8) (7329.4 8059.8)) (nil (7330.5 8074.8) (7330.5 8082.1)) (nil (7020.1 8074.8) (7016.1 8074.8)) (nil (7020.1 8059.8) (7020.1 8074.8)) (nil (6930.1 8059.8) (6930.1 8074.8)) (nil (7013.3 7980.4) (7017.3 7980.4)) (nil (7013.3 8059.8) (7013.3 7980.4)) (nil (7017.3 7980.4) (7017.3 8059.8)) (nil (7016.1 8063.8) (7016.1 8074.8)) (nil (7017.3 8063.8) (7016.1 8063.8)) (nil (7017.3 8059.8) (7017.3 8063.8)) (nil (7020.1 8059.8) (7017.3 8059.8)) (nil (7020.1 8074.8) (7020.1 8059.8)) (nil (6930.1 8074.8) (6934.1 8074.8)) (nil (6930.1 8059.8) (6930.1 8074.8)) (nil (6932.9 8059.8) (6930.1 8059.8)) (nil (6932.9 8063.8) (6932.9 8059.8)) (nil (6934.1 8063.8) (6932.9 8063.8)) (nil (6934.1 8074.8) (6934.1 8063.8)) (nil (6932.9 8059.8) (6943.5 8030.9) (6962.5 8006.6) (6987.8 7989.2) (7017.3 7980.4)) (nil (6930.1 8059.8) (6930.1 8074.8)) (nil (7020.1 8059.8) (7020.1 8074.8)) (nil (7021.2 8059.8) (7021.2 8052.4)) (nil (7200.1 7924.8) (7196.1 7924.8)) (nil (7200.1 7939.8) (7200.1 7924.8)) (nil (7110.1 7939.8) (7110.1 7924.8)) (nil (7193.3 8019.2) (7197.3 8019.2)) (nil (7193.3 7939.8) (7193.3 8019.2)) (nil (7197.3 8019.2) (7197.3 7939.8)) (nil (7196.1 7935.8) (7196.1 7924.8)) (nil (7197.3 7935.8) (7196.1 7935.8)) (nil (7197.3 7939.8) (7197.3 7935.8)) (nil (7200.1 7939.8) (7197.3 7939.8)) (nil (7200.1 7924.8) (7200.1 7939.8)) (nil (7110.1 7924.8) (7114.1 7924.8)) (nil (7110.1 7939.8) (7110.1 7924.8)) (nil (7112.9 7939.8) (7110.1 7939.8)) (nil (7112.9 7935.8) (7112.9 7939.8)) (nil (7114.1 7935.8) (7112.9 7935.8)) (nil (7114.1 7924.8) (7114.1 7935.8)) (nil (7197.3 8019.2) (7167.9 8010.4) (7142.5 7993.0) (7123.6 7968.7) (7112.9 7939.8)) (nil (7110.1 7939.8) (7110.1 7924.8)) (nil (7200.1 7939.8) (7200.1 7924.8)) (nil (7201.3 7939.8) (7201.3 7947.1)) (nil (7035.1 7939.8) (7035.1 8059.8)) (nil (7020.1 7939.8) (7020.1 8059.8)) (nil (7329.4 8059.8) (7329.4 8074.8)) (nil (7200.1 7924.8) (7242.2 7924.8)) (nil (7325.4 7939.8) (7542.7 7939.8)) (nil (7226.4 7939.8) (7243.4 7939.8)) (nil (7193.3 7939.8) (7211.4 7939.8)) (nil (6843.9 7939.8) (7112.9 7939.8)) (nil (7322.7 8074.8) (7406.4 8074.9)) (nil (7016.1 8074.8) (7242.2 8074.8)) (nil (6883.3 8074.7) (6934.1 8074.7)) (nil (7329.4 8059.8) (7421.5 8059.9)) (nil (7226.4 8059.8) (7239.4 8059.8)) (nil (7013.3 8059.8) (7211.4 8059.8)) (nil (6883.3 8059.7) (6932.9 8059.7)) (nil (7541.4 7939.8) (7520.0 7939.8)) (nil (7211.4 8059.8) (7211.4 7939.8)) (nil (7226.4 8059.8) (7226.4 7939.8)) (nil (7346.4 8059.8) (7346.4 7939.8)) (nil (7371.4 8059.8) (7371.4 7939.8)) (nil (7396.4 8059.8) (7396.4 7939.8)) (nil (7421.4 8059.8) (7421.4 7939.8)) (nil (7421.4 8084.8) (7531.4 8084.8)) (nil (7421.4 8109.8) (7531.4 8109.8)) (nil (7421.4 8134.8) (7531.4 8134.8)) (nil (7421.4 8159.8) (7531.4 8159.8)) (nil (7421.4 8184.8) (7531.4 8184.8)) (nil (7421.4 8209.8) (7531.4 8209.8)) (nil (7421.4 8234.8) (7531.4 8234.8)) (nil (7421.4 8259.8) (7531.4 8259.8)) (nil (7421.4 8284.8) (7531.4 8284.8)) (nil (7421.4 8309.8) (7531.4 8309.8)) (nil (7421.4 8334.8) (7541.4 8334.8)) (nil (7421.4 8059.8) (7421.4 8049.8)) (nil (7541.4 8059.8) (7421.4 8059.8)) (nil (7421.4 8059.8) (7421.4 8049.8)) (nil (7421.4 8059.8) (7421.4 8049.8)) (nil (7421.4 8084.8) (7541.4 8084.8)) (nil (7421.4 8109.8) (7541.4 8109.8)) (nil (7421.4 8134.8) (7541.4 8134.8)) (nil (7421.4 8159.8) (7541.4 8159.8)) (nil (7421.4 8184.8) (7541.4 8184.8)) (nil (7421.4 8209.8) (7541.4 8209.8)) (nil (7421.4 8234.8) (7541.4 8234.8)) (nil (7421.4 8259.8) (7541.4 8259.8)) (nil (7421.4 8284.8) (7541.4 8284.8)) (nil (7421.4 8309.8) (7541.4 8309.8)) (nil (7421.4 8334.8) (7538.4 8334.8)) (nil (7421.4 8059.8) (7421.4 8334.8)) (nil (7421.4 8304.8) (7421.4 8319.8)) (nil (8693.0 2066.9) (6345.8 5352.9) (1517.3 6484.5) (1058.6 6932.1) (5479.1 8059.4) (5998.2 8156.3) (7170.0 8375.1) (7688.3 8471.9) (8852.2 8689.2) (8852.0 5259.7) (8851.8 2089.4)) (nil (8689.1 2059.4) (6341.4 5346.3) (1513.5 6477.7) (1043.8 6936.1) (5477.5 8066.7) (5996.8 8163.7) (7168.6 8382.5) (7686.9 8479.3) (8859.7 8698.3) (8859.5 5259.7) (8859.3 2089.4)) (nil (6873.3 5242.1) (6425.0 5242.1)) (nil (6873.3 5257.1) (6414.3 5257.1)) (nil (7413.3 8420.5) (7041.2 8351.1)) (nil (6828.9 7670.1) (7420.9 7670.3)) (nil (6828.9 7655.1) (7420.9 7655.3)) (nil (6843.9 7655.1) (6843.9 8312.3)) (nil (6828.9 7655.1) (6828.9 8312.3)) (nil (7411.2 8431.9) (7411.1 8432.2)) (nil (7411.1 8431.9) (7411.1 8432.2)) (nil (7398.3 7655.0) (7399.5 7655.0)) (nil (6893.3 5242.1) (6893.3 6260.2)) (nil (6873.3 5242.1) (6873.3 6260.2)) (nil (1023.6 6952.3) (1025.0 6946.5)) (nil (5807.7 6742.9) (5898.4 6742.9)) (nil (5829.0 6726.7) (5829.0 6759.1)) (T (5839.8 6742.9) (5839.4 6745.7) (5838.3 6748.3) (5836.6 6750.5) (5834.4 6752.2) (5831.8 6753.3) (5829.0 6753.7) (5826.2 6753.3) (5823.6 6752.2) (5821.3 6750.5) (5819.6 6748.3) (5818.6 6745.7) (5818.2 6742.9) (5818.6 6740.1) (5819.6 6737.5) (5821.3 6735.3) (5823.6 6733.5) (5826.2 6732.5) (5829.0 6732.1) (5831.8 6732.5) (5834.4 6733.5) (5836.6 6735.3) (5838.3 6737.5) (5839.4 6740.1) (5839.8 6742.9)) (nil (7981.8 5937.5) (8072.6 5937.5)) (nil (8003.1 5921.4) (8003.1 5953.7)) (T (8013.9 5937.5) (8013.5 5940.3) (8012.5 5942.9) (8010.7 5945.1) (8008.5 5946.9) (8005.9 5947.9) (8003.1 5948.3) (8000.3 5947.9) (7997.7 5946.9) (7995.5 5945.1) (7993.8 5942.9) (7992.7 5940.3) (7992.3 5937.5) (7992.7 5934.7) (7993.8 5932.1) (7995.5 5929.9) (7997.7 5928.2) (8000.3 5927.1) (8003.1 5926.7) (8005.9 5927.1) (8008.5 5928.2) (8010.7 5929.9) (8012.5 5932.1) (8013.5 5934.7) (8013.9 5937.5)) (nil (7406.4 8074.9) (7406.4 8421.4)) (nil (7406.4 7654.4) (7406.4 7924.8)) (nil (7421.3 8059.9) (7421.4 8421.4)) (nil (7421.4 7654.4) (7421.4 7924.8)) (nil (6893.3 6919.4) (6893.3 7655.1)) (nil (6873.3 6919.4) (6873.3 7655.1)) (nil (6893.3 6319.4) (6893.3 6859.4)) (nil (6873.3 6319.4) (6873.3 6859.4)) (nil (8726.2 8673.7) (8728.0 8661.8)) (nil (8554.1 8641.2) (8555.9 8629.3)) (nil (8627.8 8655.6) (8629.5 8643.7)) (T (8859.7 5527.1) (8859.7 5530.1) (8849.7 5530.1) (8849.7 5527.1)) (T (8859.7 5523.1) (8859.7 5530.1) (8861.7 5530.1) (8861.7 5523.1)) (T (8847.7 5523.0) (8847.7 5530.0) (8849.7 5530.1) (8849.7 5523.1)) (T (8859.7 5627.1) (8859.7 5624.1) (8849.7 5624.0) (8849.7 5627.0)) (T (8859.7 5631.1) (8859.7 5624.1) (8861.7 5624.1) (8861.7 5631.1)) (T (8847.7 5631.0) (8847.7 5624.0) (8849.7 5624.0) (8849.7 5631.0)) (T (8861.7 5530.1) (8861.7 5624.1) (8856.7 5624.1) (8856.7 5530.1)) (nil (8861.7 5624.1) (8861.7 5530.1) (8955.7 5530.1)) (nil (8861.7 5624.1) (8886.0 5620.9) (8908.7 5611.5) (8928.1 5596.5) (8943.1 5577.1) (8952.5 5554.4) (8955.7 5530.1)) (T (7615.2 3576.3) (7613.5 3578.7) (7605.3 3572.9) (7607.1 3570.4)) (T (7617.5 3573.0) (7613.5 3578.7) (7615.1 3579.9) (7619.2 3574.2)) (T (7607.8 3566.0) (7603.7 3571.7) (7605.3 3572.9) (7609.4 3567.2)) (T (7556.9 3657.5) (7558.6 3655.0) (7550.5 3649.2) (7548.8 3651.6)) (T (7554.5 3660.7) (7558.6 3655.0) (7560.3 3656.2) (7556.2 3661.9)) (T (7544.8 3653.7) (7548.9 3648.0) (7550.5 3649.2) (7546.4 3654.9)) (T (7615.1 3579.9) (7560.3 3656.2) (7556.2 3653.3) (7611.0 3576.9)) (nil (7560.3 3656.2) (7615.1 3579.9) (7691.4 3634.7)) (nil (7560.3 3656.2) (7581.9 3667.8) (7605.8 3673.4) (7630.3 3672.6) (7653.8 3665.5) (7674.6 3652.6) (7691.4 3634.7))) ((6925.9 8023.5 22.0 "ABDESTHANE") (6925.9 7987.5 16.0 "1,9 m\\U+00B2") (7095.1 8023.6 22.0 "ABDESTHANE") (7095.1 7987.6 16.0 "1,6 m\\U+00B2") (7125.1 7779.9 22.0 "KADIN MESC\\U+0130T") (7125.1 7743.9 16.0 "15,0 m\\U+00B2") (7125.1 8285.5 22.0 "ERKEK MESC\\U+0130T") (7125.1 8249.5 16.0 "15,9 m\\U+00B2")))
   ("BK" "CLD_P2_MIMARI_ZK_V2" ((nil (7626.7 7918.6) (7486.7 7918.6)) (nil (7606.7 8448.2) (7606.7 7938.6)) (nil (7606.7 7938.6) (7486.7 7938.6)) (nil (7486.7 8088.6) (7596.7 8088.6)) (nil (7486.7 8113.6) (7596.7 8113.6)) (nil (7486.7 8138.6) (7596.7 8138.6)) (nil (7486.7 8163.6) (7596.7 8163.6)) (nil (7486.7 8188.6) (7596.7 8188.6)) (nil (7486.7 8213.6) (7596.7 8213.6)) (nil (7486.7 8238.6) (7596.7 8238.6)) (nil (7486.7 8263.6) (7596.7 8263.6)) (nil (7486.7 8288.6) (7596.7 8288.6)) (nil (7486.7 8313.6) (7596.7 8313.6)) (nil (7486.7 8338.6) (7606.7 8338.6)) (nil (7606.7 8063.6) (7486.7 8063.6)) (nil (7486.7 8088.6) (7606.7 8088.6)) (nil (7486.7 8113.6) (7606.7 8113.6)) (nil (7486.7 8138.6) (7606.7 8138.6)) (nil (7486.7 8163.6) (7606.7 8163.6)) (nil (7486.7 8188.6) (7606.7 8188.6)) (nil (7486.7 8213.6) (7606.7 8213.6)) (nil (7486.7 8238.6) (7606.7 8238.6)) (nil (7486.7 8263.6) (7606.7 8263.6)) (nil (7486.7 8288.6) (7606.7 8288.6)) (nil (7486.7 8313.6) (7606.7 8313.6)) (nil (7486.7 8338.6) (7603.7 8338.6)) (nil (7486.7 8063.6) (7486.7 8338.6)) (nil (7486.7 8308.6) (7486.7 8323.6)) (nil (8849.7 2070.6) (8758.3 2070.6) (6411.2 5356.7) (1582.6 6488.3) (1124.0 6935.9) (5544.5 8063.1) (6063.5 8160.0) (7235.3 8378.8) (7753.6 8475.6) (8917.5 8693.0) (8917.3 5263.4) (8917.2 2093.1)) (nil (8849.7 2063.1) (8754.5 2063.1) (6406.7 5350.0) (1578.9 6481.4) (1109.2 6939.9) (5542.9 8070.4) (6062.2 8167.4) (7233.9 8386.2) (7752.3 8483.0) (8925.0 8702.0) (8924.8 5263.4) (8924.7 2093.1)) (nil (6938.7 5245.8) (6490.4 5245.8)) (nil (6938.7 5260.8) (6479.6 5260.8)) (nil (7017.5 8286.0) (7006.6 8345.1)) (nil (7274.7 7878.9) (7274.7 7718.9)) (nil (7284.7 7868.9) (7284.7 7718.9)) (nil (7174.2 7868.8) (7174.2 7718.8)) (nil (7164.2 7868.8) (7164.2 7718.8)) (nil (7122.3 8269.1) (7106.5 8354.8)) (nil (7064.2 7868.8) (7064.2 7718.8)) (nil (7054.2 7868.8) (7054.2 7718.8)) (nil (7426.3 8063.6) (7426.3 7718.9)) (nil (7426.3 8353.6) (7426.3 8063.6)) (nil (7274.7 7878.8) (6954.2 7878.8)) (nil (7426.3 7878.9) (7274.7 7878.9)) (nil (7054.2 7868.8) (6954.2 7868.8)) (nil (7164.2 7868.8) (7064.2 7868.8)) (nil (7264.2 7868.8) (7174.2 7868.8)) (nil (7426.3 7868.9) (7284.7 7868.9)) (nil (6954.2 7718.8) (7426.3 7718.9)) (nil (7168.0 8306.1) (7168.0 8150.4)) (nil (7148.0 8302.4) (7148.0 8170.4)) (nil (6954.2 8279.2) (6954.2 7718.8)) (nil (7168.0 8150.4) (6954.2 8150.4)) (nil (7148.0 8170.4) (6954.2 8170.4)) (nil (7017.5 8286.0) (6955.0 8274.5)) (nil (7148.0 8302.4) (7117.2 8296.8)) (nil (7426.3 8353.6) (7168.0 8306.1)) (nil (6981.3 8344.4) (6894.2 8328.4)) (nil (7478.6 8424.3) (7106.5 8354.8)) (nil (6894.2 7658.8) (7486.3 7659.0)) (nil (6894.2 7658.8) (6894.2 8316.0)) (nil (7476.5 8435.6) (7476.4 8435.9)) (nil (7463.6 7658.8) (7464.9 7658.8)) (nil (6958.7 5245.8) (6958.7 6263.9)) (nil (6938.7 5245.8) (6938.7 6263.9)) (nil (1088.9 6956.1) (1090.4 6950.3)) (nil (5873.1 6746.6) (5963.8 6746.6)) (nil (5894.3 6730.4) (5894.3 6762.8)) (T (5905.1 6746.6) (5904.7 6749.4) (5903.7 6752.0) (5902.0 6754.2) (5899.7 6756.0) (5897.1 6757.0) (5894.3 6757.4) (5891.5 6757.0) (5888.9 6756.0) (5886.7 6754.2) (5885.0 6752.0) (5883.9 6749.4) (5883.5 6746.6) (5883.9 6743.8) (5885.0 6741.2) (5886.7 6739.0) (5888.9 6737.3) (5891.5 6736.2) (5894.3 6735.8) (5897.1 6736.2) (5899.7 6737.3) (5902.0 6739.0) (5903.7 6741.2) (5904.7 6743.8) (5905.1 6746.6)) (nil (8047.2 5941.3) (8137.9 5941.3)) (nil (8068.5 5925.1) (8068.5 5957.4)) (T (8079.3 5941.3) (8078.9 5944.1) (8077.8 5946.6) (8076.1 5948.9) (8073.9 5950.6) (8071.3 5951.7) (8068.5 5952.0) (8065.7 5951.7) (8063.1 5950.6) (8060.9 5948.9) (8059.1 5946.6) (8058.1 5944.1) (8057.7 5941.3) (8058.1 5938.5) (8059.1 5935.9) (8060.9 5933.6) (8063.1 5931.9) (8065.7 5930.9) (8068.5 5930.5) (8071.3 5930.9) (8073.9 5931.9) (8076.1 5933.6) (8077.8 5935.9) (8078.9 5938.5) (8079.3 5941.3)) (nil (7486.7 7658.1) (7486.7 8425.2)) (nil (6986.2 7658.1) (7486.7 7658.1)) (nil (6958.7 6923.1) (6958.7 7613.1)) (nil (6938.7 6923.1) (6938.7 7613.1)) (nil (6958.7 6323.1) (6958.7 6863.1)) (nil (6938.7 6323.1) (6938.7 6863.1)) (nil (8791.6 8677.5) (8793.3 8665.6)) (nil (8619.5 8644.9) (8621.2 8633.1)) (nil (8693.2 8659.4) (8694.9 8647.5)) (nil (8754.5 2063.1) (6406.7 5350.0) (1578.9 6481.4) (1109.2 6939.9) (5542.9 8070.4) (6062.2 8167.4) (7233.9 8386.2) (7752.3 8483.0) (8925.0 8702.0) (8924.8 5263.4) (8924.7 2093.1)) (T (1808.0 7119.5) (1805.1 7118.7) (1807.6 7109.0) (1810.5 7109.8)) (T (1811.9 7120.5) (1805.1 7118.7) (1804.6 7120.7) (1811.4 7122.4)) (T (1814.8 7108.8) (1808.0 7107.1) (1807.6 7109.0) (1814.3 7110.8)) (T (1711.1 7094.8) (1714.0 7095.5) (1716.5 7085.8) (1713.6 7085.1)) (T (1707.2 7093.8) (1714.0 7095.5) (1713.5 7097.4) (1706.7 7095.7)) (T (1710.2 7082.2) (1717.0 7083.9) (1716.5 7085.8) (1709.7 7084.1)) (T (1804.6 7120.7) (1713.5 7097.4) (1714.7 7092.6) (1805.8 7115.8)) (nil (1713.5 7097.4) (1804.6 7120.7) (1781.4 7211.8)) (nil (1713.5 7097.4) (1710.6 7121.8) (1714.1 7146.1) (1723.8 7168.7) (1738.9 7187.9) (1758.6 7202.6) (1781.4 7211.8)) (T (6288.5 8209.7) (6291.4 8210.2) (6293.3 8200.4) (6290.3 8199.8)) (T (6284.5 8208.9) (6291.4 8210.2) (6291.1 8212.2) (6284.2 8210.9)) (T (6286.8 8197.1) (6293.6 8198.4) (6293.3 8200.4) (6286.4 8199.1)) (T (6386.8 8228.0) (6383.8 8227.5) (6385.7 8217.6) (6388.6 8218.2)) (T (6390.7 8228.8) (6383.8 8227.5) (6383.5 8229.4) (6390.3 8230.7)) (T (6392.9 8217.0) (6386.0 8215.7) (6385.7 8217.6) (6392.5 8218.9)) (T (6291.1 8212.2) (6383.5 8229.4) (6384.4 8224.5) (6292.0 8207.3)) (nil (6383.5 8229.4) (6291.1 8212.2) (6273.8 8304.6)) (nil (6383.5 8229.4) (6375.9 8252.8) (6362.5 8273.3) (6344.2 8289.7) (6322.3 8300.8) (6298.3 8305.9) (6273.8 8304.6)) (T (7148.0 8175.2) (7148.0 8178.2) (7168.0 8178.2) (7168.0 8175.2)) (T (7148.0 8171.2) (7148.0 8178.2) (7146.0 8178.2) (7146.0 8171.2)) (T (7170.0 8171.2) (7170.0 8178.2) (7168.0 8178.2) (7168.0 8171.2)) (T (7148.0 8275.2) (7148.0 8272.2) (7168.0 8272.2) (7168.0 8275.2)) (T (7148.0 8279.2) (7148.0 8272.2) (7146.0 8272.2) (7146.0 8279.2)) (T (7170.0 8279.2) (7170.0 8272.2) (7168.0 8272.2) (7168.0 8279.2)) (T (7146.0 8178.2) (7146.0 8272.2) (7151.0 8272.2) (7151.0 8178.2)) (nil (7146.0 8272.2) (7146.0 8178.2) (7052.0 8178.2)) (nil (7146.0 8272.2) (7121.6 8269.0) (7099.0 8259.6) (7079.5 8244.6) (7064.6 8225.2) (7055.2 8202.5) (7052.0 8178.2)) (T (7288.7 7878.9) (7291.7 7878.9) (7291.7 7868.9) (7288.7 7868.9)) (T (7284.7 7878.9) (7291.7 7878.9) (7291.7 7880.9) (7284.7 7880.9)) (T (7284.7 7866.9) (7291.7 7866.9) (7291.7 7868.9) (7284.7 7868.9)) (T (7378.7 7878.9) (7375.7 7878.9) (7375.7 7868.9) (7378.7 7868.9)) (T (7382.7 7878.9) (7375.7 7878.9) (7375.7 7880.9) (7382.7 7880.9)) (T (7382.7 7866.9) (7375.7 7866.9) (7375.7 7868.9) (7382.7 7868.9)) (T (7291.7 7880.9) (7375.7 7880.9) (7375.7 7875.9) (7291.7 7875.9)) (nil (7375.7 7880.9) (7291.7 7880.9) (7291.7 7964.9)) (nil (7291.7 7964.9) (7313.5 7962.0) (7333.7 7953.6) (7351.1 7940.3) (7364.5 7922.9) (7372.9 7902.6) (7375.7 7880.9)) (T (7178.3 7878.8) (7181.3 7878.8) (7181.2 7868.8) (7178.2 7868.8)) (T (7174.3 7878.8) (7181.3 7878.8) (7181.3 7880.8) (7174.3 7880.8)) (T (7174.2 7866.8) (7181.2 7866.8) (7181.2 7868.8) (7174.2 7868.8)) (T (7258.2 7878.8) (7255.2 7878.8) (7255.2 7868.8) (7258.2 7868.8)) (T (7262.2 7878.8) (7255.2 7878.8) (7255.3 7880.8) (7262.3 7880.8)) (T (7262.2 7866.8) (7255.2 7866.8) (7255.2 7868.8) (7262.2 7868.8)) (T (7181.3 7880.8) (7255.3 7880.8) (7255.2 7875.8) (7181.2 7875.8)) (nil (7255.3 7880.8) (7181.3 7880.8) (7181.3 7954.8)) (nil (7181.3 7954.8) (7200.4 7952.3) (7218.3 7944.9) (7233.6 7933.1) (7245.3 7917.8) (7252.7 7900.0) (7255.3 7880.8)) (T (7068.3 7878.8) (7071.3 7878.8) (7071.2 7868.8) (7068.2 7868.8)) (T (7064.3 7878.8) (7071.3 7878.8) (7071.3 7880.8) (7064.3 7880.8)) (T (7064.2 7866.8) (7071.2 7866.8) (7071.2 7868.8) (7064.2 7868.8)) (T (7148.2 7878.8) (7145.2 7878.8) (7145.2 7868.8) (7148.2 7868.8)) (T (7152.2 7878.8) (7145.2 7878.8) (7145.3 7880.8) (7152.3 7880.8)) (T (7152.2 7866.8) (7145.2 7866.8) (7145.2 7868.8) (7152.2 7868.8)) (T (7071.3 7880.8) (7145.3 7880.8) (7145.2 7875.8) (7071.2 7875.8)) (nil (7145.3 7880.8) (7071.3 7880.8) (7071.3 7954.8)) (nil (7071.3 7954.8) (7090.4 7952.3) (7108.3 7944.9) (7123.6 7933.1) (7135.3 7917.8) (7142.7 7900.0) (7145.3 7880.8)) (T (6968.3 7878.8) (6971.3 7878.8) (6971.2 7868.8) (6968.2 7868.8)) (T (6964.3 7878.8) (6971.3 7878.8) (6971.3 7880.8) (6964.3 7880.8)) (T (6964.2 7866.8) (6971.2 7866.8) (6971.2 7868.8) (6964.2 7868.8)) (T (7048.2 7878.8) (7045.2 7878.8) (7045.2 7868.8) (7048.2 7868.8)) (T (7052.2 7878.8) (7045.2 7878.8) (7045.3 7880.8) (7052.3 7880.8)) (T (7052.2 7866.8) (7045.2 7866.8) (7045.2 7868.8) (7052.2 7868.8)) (T (6971.3 7880.8) (7045.3 7880.8) (7045.2 7875.8) (6971.2 7875.8)) (nil (7045.3 7880.8) (6971.3 7880.8) (6971.3 7954.8)) (nil (6971.3 7954.8) (6990.4 7952.3) (7008.3 7944.9) (7023.6 7933.1) (7035.3 7917.8) (7042.7 7900.0) (7045.3 7880.8)) (T (3160.7 6110.7) (3163.6 6110.0) (3165.9 6119.8) (3163.0 6120.5)) (T (3156.8 6111.7) (3163.6 6110.0) (3163.1 6108.1) (3156.3 6109.7)) (T (3159.5 6123.3) (3166.4 6121.7) (3165.9 6119.8) (3159.1 6121.4)) (T (3258.0 6087.7) (3255.1 6088.4) (3257.4 6098.1) (3260.3 6097.4)) (T (3261.9 6086.8) (3255.1 6088.4) (3254.6 6086.4) (3261.4 6084.8)) (T (3264.6 6098.5) (3257.8 6100.1) (3257.4 6098.1) (3264.2 6096.5)) (T (3163.1 6108.1) (3254.6 6086.4) (3255.8 6091.3) (3164.3 6113.0)) (nil (3254.6 6086.4) (3163.1 6108.1) (3141.5 6016.6)) (nil (3254.6 6086.4) (3245.9 6063.5) (3231.5 6043.6) (3212.5 6028.1) (3190.1 6018.1) (3165.9 6014.1) (3141.5 6016.6)) (T (4808.6 7883.2) (4805.7 7882.4) (4808.1 7872.7) (4811.0 7873.5)) (T (4812.5 7884.2) (4805.7 7882.4) (4805.2 7884.4) (4812.0 7886.1)) (T (4815.4 7872.5) (4808.6 7870.8) (4808.1 7872.7) (4814.9 7874.5)) (T (4711.7 7858.5) (4714.6 7859.2) (4717.1 7849.5) (4714.2 7848.8)) (T (4707.8 7857.5) (4714.6 7859.2) (4714.1 7861.1) (4707.3 7859.4)) (T (4710.8 7845.9) (4717.6 7847.6) (4717.1 7849.5) (4710.3 7847.8)) (T (4805.2 7884.4) (4714.1 7861.1) (4715.3 7856.3) (4806.4 7879.5)) (nil (4714.1 7861.1) (4805.2 7884.4) (4782.0 7975.5)) (nil (4714.1 7861.1) (4711.2 7885.5) (4714.7 7909.8) (4724.3 7932.4) (4739.5 7951.6) (4759.2 7966.3) (4782.0 7975.5)) (T (8791.6 8677.5) (8788.6 8676.9) (8790.4 8667.1) (8793.4 8667.6)) (T (8795.5 8678.2) (8788.6 8676.9) (8788.3 8678.9) (8795.2 8680.2)) (T (8797.7 8666.4) (8790.8 8665.1) (8790.4 8667.1) (8797.3 8668.4)) (T (8693.2 8659.4) (8696.2 8659.9) (8698.0 8650.1) (8695.0 8649.5)) (T (8689.3 8658.6) (8696.2 8659.9) (8695.8 8661.9) (8688.9 8660.6)) (T (8691.5 8646.8) (8698.4 8648.1) (8698.0 8650.1) (8691.1 8648.8)) (T (8788.3 8678.9) (8695.8 8661.9) (8696.7 8657.0) (8789.2 8674.0)) (nil (8695.8 8661.9) (8788.3 8678.9) (8771.3 8771.3)) (nil (8695.8 8661.9) (8694.6 8686.4) (8699.7 8710.4) (8710.9 8732.2) (8727.3 8750.4) (8747.9 8763.8) (8771.3 8771.3)) (T (8925.0 5530.8) (8925.0 5533.8) (8915.0 5533.8) (8915.0 5530.8)) (T (8925.0 5526.8) (8925.0 5533.8) (8927.0 5533.8) (8927.0 5526.8)) (T (8913.0 5526.8) (8913.0 5533.8) (8915.0 5533.8) (8915.0 5526.8)) (T (8925.0 5630.8) (8925.0 5627.8) (8915.0 5627.8) (8915.0 5630.8)) (T (8925.0 5634.8) (8925.0 5627.8) (8927.0 5627.8) (8927.0 5634.8)) (T (8913.0 5634.8) (8913.0 5627.8) (8915.0 5627.8) (8915.0 5634.8)) (T (8927.0 5533.8) (8927.0 5627.8) (8922.0 5627.8) (8922.0 5533.8)) (nil (8927.0 5627.8) (8927.0 5533.8) (9021.0 5533.8)) (nil (8927.0 5627.8) (8951.3 5624.6) (8974.0 5615.2) (8993.5 5600.3) (9008.4 5580.8) (9017.8 5558.1) (9021.0 5533.8)) (T (7680.6 3580.0) (7678.8 3582.4) (7670.7 3576.6) (7672.4 3574.2)) (T (7682.9 3576.7) (7678.8 3582.4) (7680.4 3583.6) (7684.5 3577.9)) (T (7673.1 3569.7) (7669.1 3575.4) (7670.7 3576.6) (7674.8 3570.9)) (T (7622.2 3661.2) (7624.0 3658.8) (7615.9 3652.9) (7614.1 3655.4)) (T (7619.9 3664.5) (7624.0 3658.8) (7625.6 3659.9) (7621.5 3665.6)) (T (7610.1 3657.5) (7614.2 3651.8) (7615.9 3652.9) (7611.8 3658.6)) (T (7680.4 3583.6) (7625.6 3659.9) (7621.5 3657.0) (7676.4 3580.7)) (nil (7625.6 3659.9) (7680.4 3583.6) (7756.8 3638.4)) (nil (7625.6 3659.9) (7647.2 3671.5) (7671.1 3677.1) (7695.7 3676.4) (7719.1 3669.3) (7740.0 3656.3) (7756.8 3638.4)) (T (6178.8 5403.4) (6181.7 5402.7) (6184.0 5412.5) (6181.1 5413.1)) (T (6174.9 5404.3) (6181.7 5402.7) (6181.3 5400.8) (6174.5 5402.4)) (T (6177.7 5416.0) (6184.5 5414.4) (6184.0 5412.5) (6177.2 5414.1)) (T (6276.1 5380.4) (6273.2 5381.1) (6275.5 5390.8) (6278.4 5390.1)) (T (6280.0 5379.5) (6273.2 5381.1) (6272.7 5379.1) (6279.6 5377.5)) (T (6282.8 5391.1) (6276.0 5392.7) (6275.5 5390.8) (6282.3 5389.2)) (T (6181.3 5400.8) (6272.7 5379.1) (6273.9 5384.0) (6182.4 5405.6)) (nil (6272.7 5379.1) (6181.3 5400.8) (6159.6 5309.3)) (nil (6272.7 5379.1) (6264.0 5356.2) (6249.7 5336.3) (6230.6 5320.8) (6208.2 5310.7) (6184.0 5306.8) (6159.6 5309.3))) ((7114.2 7814.8 22.0 "BAY WC") (7114.2 7778.8 16.0 "1,5 m\\U+00B2") (7004.2 7814.8 22.0 "BAYAN WC") (7004.2 7778.8 16.0 "1,5 m\\U+00B2") (7224.5 7814.8 22.0 "\\U+00C7\\U+00D6P ODASI") (7224.5 7778.8 16.0 "2,1 m\\U+00B2") (7032.5 8286.4 22.0 "G\\U+00DCV. HOL\\U+00DC") (7032.5 8250.4 16.0 "2,1 m\\U+00B2") (7359.3 7811.9 22.0 "JENARAT\\U+00D6R ODASI") (7359.3 7775.9 16.0 "1,5 m\\U+00B2") (7190.3 8079.4 22.0 "SI\\U+011EINAK") (7190.3 8043.4 16.0 "15,5 m\\U+00B2") (7938.0 5616.7 22.0 "\\U+00DCRET\\U+0130M ALANI") (7938.0 5580.7 16.0 "1.005,3 m\\U+00B2") (4097.1 6829.4 22.0 "\\U+00DCRET\\U+0130M ALANI") (4097.1 6793.4 16.0 "1.009,7 m\\U+00B2")))
   ("T" "CLD-P2-ICT-YAZI" 97243.5 -85552.9 160.0 0 "PARSEL 2 - ELEKTR\\U+0130K \\U+0130\\U+00C7 TES\\U+0130SAT PROJES\\U+0130")
   ("T" "CLD-P2-ICT-YAZI" 97243.5 -85782.9 50.0 0 "BROSCO \\U+0130THALAT \\U+0130HRACAT VE T\\U+0130CARET ANON\\U+0130M \\U+015E\\U+0130RKET\\U+0130 - YUKARI MAHALLE / KEMALPA\\U+015EA / \\U+0130ZM\\U+0130R")
   ("T" "CLD-P2-ICT-YAZI" 97243.5 -85862.9 38.0 0 "CLD otomatik proje  |  Disiplin 01  |  19.10.2026  |  Paftalar 1/100  |  Katman \\U+00F6neki CLD-P2-ICT-*")
   ("I" "CLD-P2-ICT-ALTLIK" "CLD_P2_MIMARI_ZK_V2" 97243.5 -96279.4 0.0 0.01)
   ("T" "CLD-P2-ICT-TABLO" 107325.2 -86202.9 26.0 0 "LEJANT")
   ("P" "CLD-P2-ICT-TABLO" T 0.0 ((107325.2 -86222.9) (108391.2 -86222.9) (108391.2 -87074.9) (107325.2 -87074.9)))
   ("I" "CLD-P2-ICT-TABLO" "CLD_S_HB" 107445.2 -86264.9 0.0 0.867)
   ("T" "CLD-P2-ICT-TABLO" 107565.2 -86264.9 20.0 7 "LED y\\U+00FCksek tavan (highbay) armat\\U+00FCr\\U+00FC 150 W, 21.000 lm, IP65")
   ("I" "CLD-P2-ICT-TABLO" "CLD_S_PNL" 107445.2 -86328.9 0.0 0.867)
   ("T" "CLD-P2-ICT-TABLO" 107565.2 -86328.9 20.0 7 "LED panel armat\\U+00FCr 60x60, 36 W, 3.600 lm, UGR<19")
   ("I" "CLD-P2-ICT-TABLO" "CLD_S_DL" 107445.2 -86392.9 0.0 1.625)
   ("T" "CLD-P2-ICT-TABLO" 107565.2 -86392.9 20.0 7 "LED downlight 18 W, 1.800 lm, IP20")
   ("I" "CLD-P2-ICT-TABLO" "CLD_S_DLB" 107445.2 -86456.9 0.0 1.625)
   ("T" "CLD-P2-ICT-TABLO" 107565.2 -86456.9 20.0 7 "LED downlight 12 W, 1.200 lm, IP44 (\\U+0131slak hacim)")
   ("I" "CLD-P2-ICT-TABLO" "CLD_S_ETJ" 107445.2 -86520.9 0.0 0.433)
   ("T" "CLD-P2-ICT-TABLO" 107565.2 -86520.9 20.0 7 "LED etanj armat\\U+00FCr 36 W, 4.000 lm, IP65")
   ("I" "CLD-P2-ICT-TABLO" "CLD_S_ACIL" 107445.2 -86584.9 0.0 1.625)
   ("T" "CLD-P2-ICT-TABLO" 107565.2 -86584.9 20.0 7 "LED acil ayd\\U+0131nlatma armat\\U+00FCr\\U+00FC 3 W, 3 saat, s\\U+00FCrekli/s\\U+00FCrekli olmayan")
   ("I" "CLD-P2-ICT-TABLO" "CLD_S_EXIT" 107445.2 -86648.9 0.0 1.3)
   ("T" "CLD-P2-ICT-TABLO" 107565.2 -86648.9 20.0 7 "LED \\U+00E7\\U+0131k\\U+0131\\U+015F/y\\U+00F6nlendirme armat\\U+00FCr\\U+00FC 3 W, 3 saat")
   ("T" "CLD-P2-ICT-TABLO" 107565.2 -86712.9 20.0 7 "AK: 3 saat acil kitli armat\\U+00FCr (s\\U+00FCrekli faz ile beslenir)")
   ("I" "CLD-P2-ICT-TABLO" "CLD_S_ANH1" 107445.2 -86776.9 0.0 1.733)
   ("T" "CLD-P2-ICT-TABLO" 107565.2 -86776.9 20.0 7 "Adi anahtar (h=110 cm)")
   ("I" "CLD-P2-ICT-TABLO" "CLD_S_ANH2" 107445.2 -86840.9 0.0 1.733)
   ("T" "CLD-P2-ICT-TABLO" 107565.2 -86840.9 20.0 7 "Kom\\U+00FCtat\\U+00F6r anahtar")
   ("I" "CLD-P2-ICT-TABLO" "CLD_S_VAV" 107445.2 -86904.9 0.0 1.3)
   ("T" "CLD-P2-ICT-TABLO" 107565.2 -86904.9 20.0 7 "Vavien anahtar")
   ("I" "CLD-P2-ICT-TABLO" "CLD_S_TP" 107445.2 -86968.9 0.0 1.04)
   ("T" "CLD-P2-ICT-TABLO" 107565.2 -86968.9 20.0 7 "Tali da\\U+011F\\U+0131t\\U+0131m panosu (UTP / \\U+0130DP)")
   ("P" "CLD-P2-ICT-LINYE-AYD" nil 0.0 ((107345.2 -87032.9) (107545.2 -87032.9)))
   ("T" "CLD-P2-ICT-TABLO" 107565.2 -87032.9 20.0 7 "Ayd\\U+0131nlatma linyesi, ok: panoya d\\U+00F6n\\U+00FC\\U+015F, etiket PANO/L\\U+0130NYE")
   ("P" "CLD-P2-ICT-PAFTA" nil 6.0 ((107175.2 -96299.4) (107175.2 -86052.9)))
   ("P" "CLD-P2-ICT-PAFTA" T 10.0 ((97143.5 -96979.4) (108641.2 -96979.4) (108641.2 -86052.9) (97143.5 -86052.9)))
   ("P" "CLD-P2-ICT-PAFTA" nil 6.0 ((97143.5 -96299.4) (108641.2 -96299.4)))
   ("P" "CLD-P2-ICT-PAFTA" T 6.0 ((106141.2 -96979.4) (108641.2 -96979.4) (108641.2 -96299.4) (106141.2 -96299.4)))
   ("T" "CLD-P2-ICT-YAZI" 106171.2 -96362.5 18.0 0 "\\U+0130\\U+015E\\U+0130N ADI")
   ("T" "CLD-P2-ICT-YAZI" 106761.2 -96362.5 20.0 0 "ELEKTR\\U+0130K \\U+0130\\U+00C7 TES\\U+0130SAT PROJES\\U+0130")
   ("L" "CLD-P2-ICT-PAFTA" 106141.2 -96396.5 108641.2 -96396.5)
   ("T" "CLD-P2-ICT-YAZI" 106171.2 -96459.6 18.0 0 "YAPI SAH\\U+0130B\\U+0130")
   ("T" "CLD-P2-ICT-YAZI" 106761.2 -96459.6 20.0 0 "BROSCO \\U+0130THALAT \\U+0130HRACAT VE T\\U+0130CARET ANON\\U+0130M \\U+015E\\U+0130RKET\\U+0130")
   ("L" "CLD-P2-ICT-PAFTA" 106141.2 -96493.6 108641.2 -96493.6)
   ("T" "CLD-P2-ICT-YAZI" 106171.2 -96556.8 18.0 0 "ADRES")
   ("T" "CLD-P2-ICT-YAZI" 106761.2 -96556.8 20.0 0 "YUKARI MAHALLE / KEMALPA\\U+015EA / \\U+0130ZM\\U+0130R  -  Ada: ......  Parsel: 2")
   ("L" "CLD-P2-ICT-PAFTA" 106141.2 -96590.8 108641.2 -96590.8)
   ("T" "CLD-P2-ICT-YAZI" 106171.2 -96653.9 18.0 0 "PAFTA ADI")
   ("T" "CLD-P2-ICT-YAZI" 106761.2 -96653.9 20.0 0 "AYDINLATMA TES\\U+0130SATI PLANI - ZEM\\U+0130N KAT PLANI")
   ("L" "CLD-P2-ICT-PAFTA" 106141.2 -96687.9 108641.2 -96687.9)
   ("T" "CLD-P2-ICT-YAZI" 106171.2 -96751.1 18.0 0 "\\U+00D6L\\U+00C7EK / TAR\\U+0130H / PAFTA NO")
   ("T" "CLD-P2-ICT-YAZI" 106761.2 -96751.1 20.0 0 "1/100   |   19.10.2026   |   01-01")
   ("L" "CLD-P2-ICT-PAFTA" 106141.2 -96785.1 108641.2 -96785.1)
   ("T" "CLD-P2-ICT-YAZI" 106171.2 -96848.2 18.0 0 "PROJE M\\U+00DCELL\\U+0130F\\U+0130")
   ("T" "CLD-P2-ICT-YAZI" 106761.2 -96848.2 20.0 0 "Elektrik M\\U+00FChendisi - Ad\\U+0131 Soyad\\U+0131: ..............................")
   ("L" "CLD-P2-ICT-PAFTA" 106141.2 -96882.2 108641.2 -96882.2)
   ("T" "CLD-P2-ICT-YAZI" 106171.2 -96945.4 18.0 0 "ODA S\\U+0130C\\U+0130L / SMM NO")
   ("T" "CLD-P2-ICT-YAZI" 106761.2 -96945.4 20.0 0 "EMO Sicil No: ............   SMM Belge No: ............   \\U+0130mza: ............")
   ("L" "CLD-P2-ICT-PAFTA" 106731.2 -96979.4 106731.2 -96299.4)
   ("T" "CLD-P2-ICT-YAZI" 97243.5 -96439.4 70.0 0 "AYDINLATMA TES\\U+0130SATI PLANI")
   ("T" "CLD-P2-ICT-YAZI" 97243.5 -96579.4 40.0 0 "ZEM\\U+0130N KAT PLANI  -  \\U+00D6: 1/100")
   ("T" "CLD-P2-ICT-YAZI" 97243.5 -96679.4 30.0 0 "Parsel 2  |  BROSCO \\U+0130THALAT \\U+0130HRACAT VE T\\U+0130CARET ANON\\U+0130M \\U+015E\\U+0130RKET\\U+0130")
   ("T" "CLD-P2-ICT-YAZI" 97243.5 -96759.4 26.0 0 "CLD - 19.10.2026 - mimari altl\\U+0131k: BROSCO 2 NOLU PARSEL M\\U+0130MAR\\U+0130.dwg")
   ("I" "CLD-P2-ICT-PANO" "CLD_S_TP" 101843.0 -90462.2 1.3406 2.5)
   ("T" "CLD-P2-ICT-PANO" 101893.0 -90402.2 30.0 0 "UTP-1")
   ("I" "CLD-P2-ICT-PANO" "CLD_S_TP" 106125.8 -90575.0 3.1415 2.5)
   ("T" "CLD-P2-ICT-PANO" 106175.8 -90515.0 30.0 0 "UTP-2")
   ("I" "CLD-P2-ICT-PANO" "CLD_S_TP" 104377.4 -88105.1 3.1416 2.5)
   ("T" "CLD-P2-ICT-PANO" 104427.4 -88045.1 30.0 0 "IDP-ZK")
   ("I" "CLD-P2-ICT-AYDINLATMA" "CLD_S_DLB" 104357.7 -88448.0 0.0 2.5)
   ("I" "CLD-P2-ICT-AYDINLATMA" "CLD_S_DLB" 104247.7 -88448.0 0.0 2.5)
   ("I" "CLD-P2-ICT-AYDINLATMA" "CLD_S_ETJ" 104467.9 -88440.5 0.0 1.0)
   ("I" "CLD-P2-ICT-AYDINLATMA" "CLD_S_DL" 104245.6 -88062.9 0.0 2.5)
   ("I" "CLD-P2-ICT-ACIL" "CLD_S_ACIL" 104328.5 -88016.8 0.0 2.5)
   ("I" "CLD-P2-ICT-AYDINLATMA" "CLD_S_ETJ" 104602.8 -88489.5 0.0 1.0)
   ("I" "CLD-P2-ICT-ACIL" "CLD_S_ACIL" 104637.8 -88489.5 0.0 2.5)
   ("I" "CLD-P2-ICT-AYDINLATMA" "CLD_S_ETJ" 104551.7 -88163.1 0.0 1.0)
   ("I" "CLD-P2-ICT-AYDINLATMA" "CLD_S_ETJ" 104551.7 -88004.8 0.0 1.0)
   ("I" "CLD-P2-ICT-ACIL" "CLD_S_ACIL" 104586.7 -88163.1 0.0 2.5)
   ("I" "CLD-P2-ICT-ACIL" "CLD_S_EXIT" 104427.6 -88053.1 0.0 2.5)
   ("I" "CLD-P2-ICT-ACIL" "CLD_S_EXIT" 104613.1 -88338.6 0.0 2.5)
   ("I" "CLD-P2-ICT-ACIL" "CLD_S_EXIT" 104384.8 -88344.7 0.0 2.5)
   ("I" "CLD-P2-ICT-AYDINLATMA" "CLD_S_HB" 104600.6 -90913.9 0.0 1.6)
   ("T" "CLD-P2-ICT-ACIL" 104650.6 -90963.9 14.4 0 "AK")
   ("I" "CLD-P2-ICT-AYDINLATMA" "CLD_S_HB" 104600.6 -91305.4 0.0 1.6)
   ("I" "CLD-P2-ICT-AYDINLATMA" "CLD_S_HB" 104600.6 -91696.9 0.0 1.6)
   ("I" "CLD-P2-ICT-AYDINLATMA" "CLD_S_HB" 104947.4 -88956.5 0.0 1.6)
   ("I" "CLD-P2-ICT-AYDINLATMA" "CLD_S_HB" 104947.4 -89348.0 0.0 1.6)
   ("T" "CLD-P2-ICT-ACIL" 104997.4 -89398.0 14.4 0 "AK")
   ("I" "CLD-P2-ICT-AYDINLATMA" "CLD_S_HB" 104947.4 -89739.5 0.0 1.6)
   ("I" "CLD-P2-ICT-AYDINLATMA" "CLD_S_HB" 104947.4 -90131.0 0.0 1.6)
   ("I" "CLD-P2-ICT-AYDINLATMA" "CLD_S_HB" 104947.3 -90522.5 0.0 1.6)
   ("I" "CLD-P2-ICT-AYDINLATMA" "CLD_S_HB" 104947.3 -90913.9 0.0 1.6)
   ("T" "CLD-P2-ICT-ACIL" 104997.3 -90963.9 14.4 0 "AK")
   ("I" "CLD-P2-ICT-AYDINLATMA" "CLD_S_HB" 104947.3 -91305.4 0.0 1.6)
   ("I" "CLD-P2-ICT-AYDINLATMA" "CLD_S_HB" 104947.3 -91696.9 0.0 1.6)
   ("I" "CLD-P2-ICT-AYDINLATMA" "CLD_S_HB" 104947.3 -92088.4 0.0 1.6)
   ("I" "CLD-P2-ICT-AYDINLATMA" "CLD_S_HB" 105294.2 -88173.6 0.0 1.6)
   ("T" "CLD-P2-ICT-ACIL" 105344.2 -88223.6 14.4 0 "AK")
   ("I" "CLD-P2-ICT-AYDINLATMA" "CLD_S_HB" 105294.1 -88565.0 0.0 1.6)
   ("I" "CLD-P2-ICT-AYDINLATMA" "CLD_S_HB" 105294.1 -88956.5 0.0 1.6)
   ("I" "CLD-P2-ICT-AYDINLATMA" "CLD_S_HB" 105294.1 -89348.0 0.0 1.6)
   ("I" "CLD-P2-ICT-AYDINLATMA" "CLD_S_HB" 105294.1 -89739.5 0.0 1.6)
   ("T" "CLD-P2-ICT-ACIL" 105344.1 -89789.5 14.4 0 "AK")
   ("I" "CLD-P2-ICT-AYDINLATMA" "CLD_S_HB" 105294.0 -90914.0 0.0 1.6)
   ("I" "CLD-P2-ICT-AYDINLATMA" "CLD_S_HB" 105294.0 -91305.5 0.0 1.6)
   ("I" "CLD-P2-ICT-AYDINLATMA" "CLD_S_HB" 105294.0 -91696.9 0.0 1.6)
   ("I" "CLD-P2-ICT-AYDINLATMA" "CLD_S_HB" 105294.0 -92088.4 0.0 1.6)
   ("T" "CLD-P2-ICT-ACIL" 105344.0 -92138.4 14.4 0 "AK")
   ("I" "CLD-P2-ICT-AYDINLATMA" "CLD_S_HB" 105293.9 -92479.9 0.0 1.6)
   ("I" "CLD-P2-ICT-AYDINLATMA" "CLD_S_HB" 105640.9 -88173.6 0.0 1.6)
   ("I" "CLD-P2-ICT-AYDINLATMA" "CLD_S_HB" 105640.9 -88565.1 0.0 1.6)
   ("I" "CLD-P2-ICT-AYDINLATMA" "CLD_S_HB" 105640.8 -88956.6 0.0 1.6)
   ("T" "CLD-P2-ICT-ACIL" 105690.8 -89006.6 14.4 0 "AK")
   ("I" "CLD-P2-ICT-AYDINLATMA" "CLD_S_HB" 105640.8 -89348.0 0.0 1.6)
   ("I" "CLD-P2-ICT-AYDINLATMA" "CLD_S_HB" 105640.8 -89739.5 0.0 1.6)
   ("I" "CLD-P2-ICT-AYDINLATMA" "CLD_S_HB" 105640.8 -90131.0 0.0 1.6)
   ("I" "CLD-P2-ICT-AYDINLATMA" "CLD_S_HB" 105640.8 -90522.5 0.0 1.6)
   ("T" "CLD-P2-ICT-ACIL" 105690.8 -90572.5 14.4 0 "AK")
   ("I" "CLD-P2-ICT-AYDINLATMA" "CLD_S_HB" 105640.7 -90914.0 0.0 1.6)
   ("I" "CLD-P2-ICT-AYDINLATMA" "CLD_S_HB" 105640.7 -91305.5 0.0 1.6)))))
(defun cld:ops-p2_elektrik_ic_tesisat-2 () (cld:play (quote (
   ("I" "CLD-P2-ICT-AYDINLATMA" "CLD_S_HB" 105640.7 -91697.0 0.0 1.6)
   ("I" "CLD-P2-ICT-AYDINLATMA" "CLD_S_HB" 105640.7 -92088.4 0.0 1.6)
   ("T" "CLD-P2-ICT-ACIL" 105690.7 -92138.4 14.4 0 "AK")
   ("I" "CLD-P2-ICT-AYDINLATMA" "CLD_S_HB" 105640.6 -92479.9 0.0 1.6)
   ("I" "CLD-P2-ICT-AYDINLATMA" "CLD_S_HB" 105640.6 -92871.4 0.0 1.6)
   ("I" "CLD-P2-ICT-AYDINLATMA" "CLD_S_HB" 105640.6 -93262.9 0.0 1.6)
   ("I" "CLD-P2-ICT-ACIL" "CLD_S_EXIT" 105998.3 -87632.0 0.0 2.5)
   ("I" "CLD-P2-ICT-ACIL" "CLD_S_EXIT" 106145.8 -90698.6 0.0 2.5)
   ("I" "CLD-P2-ICT-ACIL" "CLD_S_EXIT" 104965.0 -92684.7 0.0 2.5)
   ("I" "CLD-P2-ICT-AYDINLATMA" "CLD_S_HB" 102645.4 -90348.5 0.0 1.6)
   ("T" "CLD-P2-ICT-ACIL" 102695.4 -90398.5 14.4 0 "AK")
   ("I" "CLD-P2-ICT-AYDINLATMA" "CLD_S_HB" 103061.5 -90270.8 0.0 1.6)
   ("I" "CLD-P2-ICT-AYDINLATMA" "CLD_S_HB" 103477.5 -90193.1 0.0 1.6)
   ("I" "CLD-P2-ICT-AYDINLATMA" "CLD_S_HB" 103893.6 -90115.4 0.0 1.6)
   ("I" "CLD-P2-ICT-AYDINLATMA" "CLD_S_HB" 102160.3 -90056.2 0.0 1.6)
   ("T" "CLD-P2-ICT-ACIL" 102210.3 -90106.2 14.4 0 "AK")
   ("I" "CLD-P2-ICT-AYDINLATMA" "CLD_S_HB" 102992.4 -89900.8 0.0 1.6)
   ("I" "CLD-P2-ICT-AYDINLATMA" "CLD_S_HB" 103408.4 -89823.1 0.0 1.6)
   ("I" "CLD-P2-ICT-AYDINLATMA" "CLD_S_HB" 103824.5 -89745.4 0.0 1.6)
   ("I" "CLD-P2-ICT-AYDINLATMA" "CLD_S_HB" 100843.1 -89919.4 0.0 1.6)
   ("T" "CLD-P2-ICT-ACIL" 100893.1 -89969.4 14.4 0 "AK")
   ("I" "CLD-P2-ICT-AYDINLATMA" "CLD_S_HB" 101259.1 -89841.7 0.0 1.6)
   ("I" "CLD-P2-ICT-AYDINLATMA" "CLD_S_HB" 101675.2 -89764.0 0.0 1.6)
   ("I" "CLD-P2-ICT-AYDINLATMA" "CLD_S_HB" 102091.2 -89686.3 0.0 1.6)
   ("I" "CLD-P2-ICT-AYDINLATMA" "CLD_S_HB" 102507.3 -89608.6 0.0 1.6)
   ("T" "CLD-P2-ICT-ACIL" 102557.3 -89658.6 14.4 0 "AK")
   ("I" "CLD-P2-ICT-AYDINLATMA" "CLD_S_HB" 103755.4 -89375.5 0.0 1.6)
   ("I" "CLD-P2-ICT-AYDINLATMA" "CLD_S_HB" 99941.9 -89704.8 0.0 1.6)
   ("I" "CLD-P2-ICT-AYDINLATMA" "CLD_S_HB" 100357.9 -89627.1 0.0 1.6)
   ("I" "CLD-P2-ICT-AYDINLATMA" "CLD_S_HB" 101190.0 -89471.7 0.0 1.6)
   ("T" "CLD-P2-ICT-ACIL" 101240.0 -89521.7 14.4 0 "AK")
   ("I" "CLD-P2-ICT-AYDINLATMA" "CLD_S_HB" 101606.1 -89394.1 0.0 1.6)
   ("I" "CLD-P2-ICT-AYDINLATMA" "CLD_S_HB" 102022.1 -89316.4 0.0 1.6)
   ("I" "CLD-P2-ICT-AYDINLATMA" "CLD_S_HB" 102438.2 -89238.7 0.0 1.6)
   ("I" "CLD-P2-ICT-AYDINLATMA" "CLD_S_HB" 102854.2 -89161.0 0.0 1.6)
   ("T" "CLD-P2-ICT-ACIL" 102904.2 -89211.0 14.4 0 "AK")
   ("I" "CLD-P2-ICT-AYDINLATMA" "CLD_S_HB" 103270.3 -89083.3 0.0 1.6)
   ("I" "CLD-P2-ICT-AYDINLATMA" "CLD_S_HB" 103686.3 -89005.6 0.0 1.6)
   ("I" "CLD-P2-ICT-AYDINLATMA" "CLD_S_HB" 99040.7 -89490.3 0.0 1.6)
   ("I" "CLD-P2-ICT-AYDINLATMA" "CLD_S_HB" 99456.8 -89412.6 0.0 1.6)
   ("T" "CLD-P2-ICT-ACIL" 99506.8 -89462.6 14.4 0 "AK")
   ("I" "CLD-P2-ICT-AYDINLATMA" "CLD_S_HB" 99872.8 -89334.9 0.0 1.6)
   ("I" "CLD-P2-ICT-AYDINLATMA" "CLD_S_HB" 100288.9 -89257.2 0.0 1.6)
   ("I" "CLD-P2-ICT-AYDINLATMA" "CLD_S_HB" 100704.9 -89179.5 0.0 1.6)
   ("I" "CLD-P2-ICT-AYDINLATMA" "CLD_S_HB" 101121.0 -89101.8 0.0 1.6)
   ("T" "CLD-P2-ICT-ACIL" 101171.0 -89151.8 14.4 0 "AK")
   ("I" "CLD-P2-ICT-AYDINLATMA" "CLD_S_HB" 101537.0 -89024.1 0.0 1.6)
   ("I" "CLD-P2-ICT-AYDINLATMA" "CLD_S_HB" 101953.1 -88946.4 0.0 1.6)
   ("I" "CLD-P2-ICT-AYDINLATMA" "CLD_S_HB" 102369.1 -88868.7 0.0 1.6)
   ("I" "CLD-P2-ICT-AYDINLATMA" "CLD_S_HB" 102785.2 -88791.0 0.0 1.6)
   ("T" "CLD-P2-ICT-ACIL" 102835.2 -88841.0 14.4 0 "AK")
   ("I" "CLD-P2-ICT-AYDINLATMA" "CLD_S_HB" 103201.2 -88713.3 0.0 1.6)
   ("I" "CLD-P2-ICT-AYDINLATMA" "CLD_S_HB" 103617.2 -88635.7 0.0 1.6)
   ("I" "CLD-P2-ICT-ACIL" "CLD_S_EXIT" 99019.6 -89192.7 0.0 2.5)
   ("I" "CLD-P2-ICT-ACIL" "CLD_S_EXIT" 103585.2 -88082.6 0.0 2.5)
   ("I" "CLD-P2-ICT-ACIL" "CLD_S_EXIT" 100458.2 -90158.2 0.0 2.5)
   ("I" "CLD-P2-ICT-ACIL" "CLD_S_EXIT" 102009.1 -88430.3 0.0 2.5)
   ("I" "CLD-P2-ICT-ACIL" "CLD_S_EXIT" 103476.3 -90865.5 0.0 2.5)
   ("I" "CLD-P2-ICT-ANAHTAR" "CLD_S_ANH1" 104288.9 -88422.9 -1.5508 2.5)
   ("I" "CLD-P2-ICT-ANAHTAR" "CLD_S_ANH1" 104186.7 -88420.3 4.6924 2.5)
   ("I" "CLD-P2-ICT-ANAHTAR" "CLD_S_ANH1" 104394.2 -88423.1 -1.5459 2.5)
   ("I" "CLD-P2-ICT-ANAHTAR" "CLD_S_ANH1" 104264.0 -88067.4 2.2253 2.5)
   ("I" "CLD-P2-ICT-ANAHTAR" "CLD_S_ANH1" 104586.5 -88438.3 4.7124 2.5)
   ("P" "CLD-P2-ICT-LINYE-AYD" nil 0.0 ((104245.6 -88062.9) (104551.7 -88163.1) (104551.7 -88004.8) (104357.7 -88448.0) (104467.9 -88440.5) (104247.7 -88448.0) (104602.8 -88489.5)))
   ("P" "CLD-P2-ICT-LINYE-AYD" nil 0.0 ((104245.6 -88062.9) (104311.5 -88084.0)))
   ("P" "CLD-P2-ICT-LINYE-AYD" nil 0.0 ((104291.4 -88064.9) (104311.5 -88084.0) (104284.1 -88087.8)))
   ("T" "CLD-P2-ICT-YAZI" 104326.5 -88069.0 18.0 0 "IDP-ZK/A1")
   ("P" "CLD-P2-ICT-LINYE-AYD" nil 0.0 ((104427.6 -88053.1) (104328.5 -88016.8) (104586.7 -88163.1) (104613.1 -88338.6) (104637.8 -88489.5) (104384.8 -88344.7)))
   ("P" "CLD-P2-ICT-LINYE-AYD" nil 0.0 ((104377.4 -88105.1) (104427.6 -88053.1)))
   ("T" "CLD-P2-ICT-YAZI" 104462.6 -88023.1 18.0 0 "IDP-ZK/AC2")
   ("P" "CLD-P2-ICT-LINYE-AYD" nil 0.0 ((104600.6 -91696.9) (104600.6 -91305.4) (104600.6 -90913.9)))
   ("P" "CLD-P2-ICT-LINYE-AYD" nil 0.0 ((104600.6 -91696.9) (104697.2 -91625.8)))
   ("P" "CLD-P2-ICT-LINYE-AYD" nil 0.0 ((104670.0 -91630.9) (104697.2 -91625.8) (104684.2 -91650.3)))
   ("T" "CLD-P2-ICT-YAZI" 104712.2 -91610.8 18.0 0 "UTP-2/A1")
   ("P" "CLD-P2-ICT-LINYE-AYD" nil 0.0 ((104947.4 -88956.5) (104947.4 -89348.0) (104947.4 -89739.5) (104947.4 -90131.0) (104947.3 -90522.5) (104947.3 -90913.9) (104947.3 -91305.4) (104947.3 -91696.9)))
   ("P" "CLD-P2-ICT-LINYE-AYD" nil 0.0 ((104947.4 -88956.5) (105018.0 -89053.5)))
   ("P" "CLD-P2-ICT-LINYE-AYD" nil 0.0 ((105013.0 -89026.3) (105018.0 -89053.5) (104993.6 -89040.4)))
   ("T" "CLD-P2-ICT-YAZI" 105033.0 -89038.5 18.0 0 "UTP-2/A2")
   ("P" "CLD-P2-ICT-LINYE-AYD" nil 0.0 ((104947.3 -92088.4) (105293.9 -92479.9) (105294.0 -92088.4) (105294.0 -91696.9) (105294.0 -91305.5) (105294.0 -90914.0) (105294.1 -89739.5) (105294.1 -89348.0)))
   ("P" "CLD-P2-ICT-LINYE-AYD" nil 0.0 ((104947.3 -92088.4) (105021.0 -91993.7)))
   ("P" "CLD-P2-ICT-LINYE-AYD" nil 0.0 ((104996.2 -92006.1) (105021.0 -91993.7) (105015.1 -92020.8)))
   ("T" "CLD-P2-ICT-YAZI" 105036.0 -91978.7 18.0 0 "UTP-2/A3")
   ("P" "CLD-P2-ICT-LINYE-AYD" nil 0.0 ((105294.1 -88956.5) (105294.1 -88565.0) (105294.2 -88173.6) (105640.9 -88173.6) (105640.9 -88565.1) (105640.8 -88956.6) (105640.8 -89348.0) (105640.8 -89739.5)))
   ("P" "CLD-P2-ICT-LINYE-AYD" nil 0.0 ((105294.1 -88956.5) (105349.0 -89063.3)))
   ("P" "CLD-P2-ICT-LINYE-AYD" nil 0.0 ((105348.2 -89035.5) (105349.0 -89063.3) (105326.9 -89046.5)))
   ("T" "CLD-P2-ICT-YAZI" 105364.0 -89048.3 18.0 0 "UTP-2/A4")
   ("P" "CLD-P2-ICT-LINYE-AYD" nil 0.0 ((105640.8 -90131.0) (105640.8 -90522.5) (105640.7 -90914.0) (105640.7 -91305.5) (105640.7 -91697.0) (105640.7 -92088.4) (105640.6 -92479.9) (105640.6 -92871.4)))
   ("P" "CLD-P2-ICT-LINYE-AYD" nil 0.0 ((105640.8 -90131.0) (105729.3 -90212.0)))
   ("P" "CLD-P2-ICT-LINYE-AYD" nil 0.0 ((105718.9 -90186.3) (105729.3 -90212.0) (105702.7 -90204.0)))
   ("T" "CLD-P2-ICT-YAZI" 105744.3 -90197.0 18.0 0 "UTP-2/A5")
   ("P" "CLD-P2-ICT-LINYE-AYD" nil 0.0 ((105640.6 -93262.9) (105661.9 -93144.8)))
   ("P" "CLD-P2-ICT-LINYE-AYD" nil 0.0 ((105645.7 -93167.3) (105661.9 -93144.8) (105669.3 -93171.5)))
   ("T" "CLD-P2-ICT-YAZI" 105676.9 -93129.8 18.0 0 "UTP-2/A6")
   ("P" "CLD-P2-ICT-LINYE-AYD" nil 0.0 ((106145.8 -90698.6) (106135.8 -90636.8)))
   ("P" "CLD-P2-ICT-LINYE-AYD" nil 0.0 ((106128.0 -90663.4) (106135.8 -90636.8) (106151.6 -90659.6)))
   ("T" "CLD-P2-ICT-YAZI" 106150.8 -90621.8 18.0 0 "UTP-2/AC7")
   ("P" "CLD-P2-ICT-LINYE-AYD" nil 0.0 ((104965.0 -92684.7) (105022.9 -92579.5)))
   ("P" "CLD-P2-ICT-LINYE-AYD" nil 0.0 ((105000.3 -92595.7) (105022.9 -92579.5) (105021.4 -92607.2)))
   ("T" "CLD-P2-ICT-YAZI" 105037.9 -92564.5 18.0 0 "UTP-2/AC7")
   ("P" "CLD-P2-ICT-LINYE-AYD" nil 0.0 ((105998.3 -87632.0) (106003.5 -87751.9)))
   ("P" "CLD-P2-ICT-LINYE-AYD" nil 0.0 ((106014.4 -87726.4) (106003.5 -87751.9) (105990.4 -87727.4)))
   ("T" "CLD-P2-ICT-YAZI" 106018.5 -87736.9 18.0 0 "UTP-2/AC8")
   ("P" "CLD-P2-ICT-LINYE-AYD" nil 0.0 ((102645.4 -90348.5) (103061.5 -90270.8) (103477.5 -90193.1) (103893.6 -90115.4) (103824.5 -89745.4) (103408.4 -89823.1) (102992.4 -89900.8) (102160.3 -90056.2)))
   ("P" "CLD-P2-ICT-LINYE-AYD" nil 0.0 ((102645.4 -90348.5) (102526.6 -90365.3)))
   ("P" "CLD-P2-ICT-LINYE-AYD" nil 0.0 ((102553.1 -90373.7) (102526.6 -90365.3) (102549.7 -90349.9)))
   ("T" "CLD-P2-ICT-YAZI" 102541.6 -90350.3 18.0 0 "UTP-1/A1")
   ("P" "CLD-P2-ICT-LINYE-AYD" nil 0.0 ((100843.1 -89919.4) (101259.1 -89841.7) (101675.2 -89764.0) (102091.2 -89686.3) (102507.3 -89608.6)))
   ("P" "CLD-P2-ICT-LINYE-AYD" nil 0.0 ((100843.1 -89919.4) (100948.5 -89976.6)))
   ("P" "CLD-P2-ICT-LINYE-AYD" nil 0.0 ((100932.3 -89954.1) (100948.5 -89976.6) (100920.8 -89975.2)))
   ("T" "CLD-P2-ICT-YAZI" 100963.5 -89961.6 18.0 0 "UTP-1/A2")
   ("P" "CLD-P2-ICT-LINYE-AYD" nil 0.0 ((103755.4 -89375.5) (103686.3 -89005.6) (103270.3 -89083.3)))
   ("P" "CLD-P2-ICT-LINYE-AYD" nil 0.0 ((103755.4 -89375.5) (103651.1 -89434.8)))
   ("P" "CLD-P2-ICT-LINYE-AYD" nil 0.0 ((103678.7 -89432.9) (103651.1 -89434.8) (103666.9 -89412.0)))
   ("T" "CLD-P2-ICT-YAZI" 103666.1 -89419.8 18.0 0 "UTP-1/A2")
   ("P" "CLD-P2-ICT-LINYE-AYD" nil 0.0 ((102854.2 -89161.0) (102438.2 -89238.7) (102022.1 -89316.4) (101606.1 -89394.1) (101190.0 -89471.7) (100357.9 -89627.1) (99941.9 -89704.8) (99040.7 -89490.3)))
   ("P" "CLD-P2-ICT-LINYE-AYD" nil 0.0 ((102854.2 -89161.0) (102780.6 -89255.7)))
   ("P" "CLD-P2-ICT-LINYE-AYD" nil 0.0 ((102805.4 -89243.3) (102780.6 -89255.7) (102786.5 -89228.6)))
   ("T" "CLD-P2-ICT-YAZI" 102795.6 -89240.7 18.0 0 "UTP-1/A3")
   ("P" "CLD-P2-ICT-LINYE-AYD" nil 0.0 ((99456.8 -89412.6) (99872.8 -89334.9) (100288.9 -89257.2) (100704.9 -89179.5) (101121.0 -89101.8) (101537.0 -89024.1) (101953.1 -88946.4) (102369.1 -88868.7)))
   ("P" "CLD-P2-ICT-LINYE-AYD" nil 0.0 ((99456.8 -89412.6) (99566.6 -89460.9)))))))
(defun cld:ops-p2_elektrik_ic_tesisat-3 () (cld:play (quote (
   ("P" "CLD-P2-ICT-LINYE-AYD" nil 0.0 ((99548.6 -89439.9) (99566.6 -89460.9) (99538.9 -89461.8)))
   ("T" "CLD-P2-ICT-YAZI" 99581.6 -89445.9 18.0 0 "UTP-1/A4")
   ("P" "CLD-P2-ICT-LINYE-AYD" nil 0.0 ((102785.2 -88791.0) (103201.2 -88713.3) (103617.2 -88635.7)))
   ("P" "CLD-P2-ICT-LINYE-AYD" nil 0.0 ((102785.2 -88791.0) (102726.2 -88895.6)))
   ("P" "CLD-P2-ICT-LINYE-AYD" nil 0.0 ((102749.0 -88879.7) (102726.2 -88895.6) (102728.0 -88867.9)))
   ("T" "CLD-P2-ICT-YAZI" 102741.2 -88880.6 18.0 0 "UTP-1/A5")
   ("P" "CLD-P2-ICT-LINYE-AYD" nil 0.0 ((100458.2 -90158.2) (100575.4 -90183.9)))
   ("P" "CLD-P2-ICT-LINYE-AYD" nil 0.0 ((100553.6 -90166.8) (100575.4 -90183.9) (100548.4 -90190.3)))
   ("T" "CLD-P2-ICT-YAZI" 100590.4 -90168.9 18.0 0 "UTP-1/AC6")
   ("P" "CLD-P2-ICT-LINYE-AYD" nil 0.0 ((99019.6 -89192.7) (99129.0 -89241.9)))
   ("P" "CLD-P2-ICT-LINYE-AYD" nil 0.0 ((99111.2 -89220.7) (99129.0 -89241.9) (99101.3 -89242.6)))
   ("T" "CLD-P2-ICT-YAZI" 99144.0 -89226.9 18.0 0 "UTP-1/AC6")
   ("P" "CLD-P2-ICT-LINYE-AYD" nil 0.0 ((102009.1 -88430.3) (101999.4 -88549.9)))
   ("P" "CLD-P2-ICT-LINYE-AYD" nil 0.0 ((102013.4 -88526.0) (101999.4 -88549.9) (101989.4 -88524.0)))
   ("T" "CLD-P2-ICT-YAZI" 102014.4 -88534.9 18.0 0 "UTP-1/AC7")
   ("P" "CLD-P2-ICT-LINYE-AYD" nil 0.0 ((103585.2 -88082.6) (103514.3 -88179.5)))
   ("P" "CLD-P2-ICT-LINYE-AYD" nil 0.0 ((103538.8 -88166.4) (103514.3 -88179.5) (103519.4 -88152.2)))
   ("T" "CLD-P2-ICT-YAZI" 103529.3 -88164.5 18.0 0 "UTP-1/AC7")
   ("P" "CLD-P2-ICT-LINYE-AYD" nil 0.0 ((103476.3 -90865.5) (103359.8 -90836.7)))
   ("P" "CLD-P2-ICT-LINYE-AYD" nil 0.0 ((103381.2 -90854.4) (103359.8 -90836.7) (103387.0 -90831.1)))
   ("T" "CLD-P2-ICT-YAZI" 103374.8 -90821.7 18.0 0 "UTP-1/AC8")
   ("I" "CLD-P2-ICT-ALTLIK" "CLD_P2_MIMARI_1K_V2" 109741.2 -96279.4 0.0 0.01)
   ("T" "CLD-P2-ICT-TABLO" 119662.1 -86202.9 26.0 0 "LEJANT")
   ("P" "CLD-P2-ICT-TABLO" T 0.0 ((119662.1 -86222.9) (120728.1 -86222.9) (120728.1 -87074.9) (119662.1 -87074.9)))
   ("I" "CLD-P2-ICT-TABLO" "CLD_S_HB" 119782.1 -86264.9 0.0 0.867)
   ("T" "CLD-P2-ICT-TABLO" 119902.1 -86264.9 20.0 7 "LED y\\U+00FCksek tavan (highbay) armat\\U+00FCr\\U+00FC 150 W, 21.000 lm, IP65")
   ("I" "CLD-P2-ICT-TABLO" "CLD_S_PNL" 119782.1 -86328.9 0.0 0.867)
   ("T" "CLD-P2-ICT-TABLO" 119902.1 -86328.9 20.0 7 "LED panel armat\\U+00FCr 60x60, 36 W, 3.600 lm, UGR<19")
   ("I" "CLD-P2-ICT-TABLO" "CLD_S_DL" 119782.1 -86392.9 0.0 1.625)
   ("T" "CLD-P2-ICT-TABLO" 119902.1 -86392.9 20.0 7 "LED downlight 18 W, 1.800 lm, IP20")
   ("I" "CLD-P2-ICT-TABLO" "CLD_S_DLB" 119782.1 -86456.9 0.0 1.625)
   ("T" "CLD-P2-ICT-TABLO" 119902.1 -86456.9 20.0 7 "LED downlight 12 W, 1.200 lm, IP44 (\\U+0131slak hacim)")
   ("I" "CLD-P2-ICT-TABLO" "CLD_S_ETJ" 119782.1 -86520.9 0.0 0.433)
   ("T" "CLD-P2-ICT-TABLO" 119902.1 -86520.9 20.0 7 "LED etanj armat\\U+00FCr 36 W, 4.000 lm, IP65")
   ("I" "CLD-P2-ICT-TABLO" "CLD_S_ACIL" 119782.1 -86584.9 0.0 1.625)
   ("T" "CLD-P2-ICT-TABLO" 119902.1 -86584.9 20.0 7 "LED acil ayd\\U+0131nlatma armat\\U+00FCr\\U+00FC 3 W, 3 saat, s\\U+00FCrekli/s\\U+00FCrekli olmayan")
   ("I" "CLD-P2-ICT-TABLO" "CLD_S_EXIT" 119782.1 -86648.9 0.0 1.3)
   ("T" "CLD-P2-ICT-TABLO" 119902.1 -86648.9 20.0 7 "LED \\U+00E7\\U+0131k\\U+0131\\U+015F/y\\U+00F6nlendirme armat\\U+00FCr\\U+00FC 3 W, 3 saat")
   ("T" "CLD-P2-ICT-TABLO" 119902.1 -86712.9 20.0 7 "AK: 3 saat acil kitli armat\\U+00FCr (s\\U+00FCrekli faz ile beslenir)")
   ("I" "CLD-P2-ICT-TABLO" "CLD_S_ANH1" 119782.1 -86776.9 0.0 1.733)
   ("T" "CLD-P2-ICT-TABLO" 119902.1 -86776.9 20.0 7 "Adi anahtar (h=110 cm)")
   ("I" "CLD-P2-ICT-TABLO" "CLD_S_ANH2" 119782.1 -86840.9 0.0 1.733)
   ("T" "CLD-P2-ICT-TABLO" 119902.1 -86840.9 20.0 7 "Kom\\U+00FCtat\\U+00F6r anahtar")
   ("I" "CLD-P2-ICT-TABLO" "CLD_S_VAV" 119782.1 -86904.9 0.0 1.3)
   ("T" "CLD-P2-ICT-TABLO" 119902.1 -86904.9 20.0 7 "Vavien anahtar")
   ("I" "CLD-P2-ICT-TABLO" "CLD_S_TP" 119782.1 -86968.9 0.0 1.04)
   ("T" "CLD-P2-ICT-TABLO" 119902.1 -86968.9 20.0 7 "Tali da\\U+011F\\U+0131t\\U+0131m panosu (UTP / \\U+0130DP)")
   ("P" "CLD-P2-ICT-LINYE-AYD" nil 0.0 ((119682.1 -87032.9) (119882.1 -87032.9)))
   ("T" "CLD-P2-ICT-TABLO" 119902.1 -87032.9 20.0 7 "Ayd\\U+0131nlatma linyesi, ok: panoya d\\U+00F6n\\U+00FC\\U+015F, etiket PANO/L\\U+0130NYE")
   ("P" "CLD-P2-ICT-PAFTA" nil 6.0 ((119512.1 -96299.4) (119512.1 -86052.9)))
   ("P" "CLD-P2-ICT-PAFTA" T 10.0 ((109641.2 -96979.4) (120978.1 -96979.4) (120978.1 -86052.9) (109641.2 -86052.9)))
   ("P" "CLD-P2-ICT-PAFTA" nil 6.0 ((109641.2 -96299.4) (120978.1 -96299.4)))
   ("P" "CLD-P2-ICT-PAFTA" T 6.0 ((118478.1 -96979.4) (120978.1 -96979.4) (120978.1 -96299.4) (118478.1 -96299.4)))
   ("T" "CLD-P2-ICT-YAZI" 118508.1 -96362.5 18.0 0 "\\U+0130\\U+015E\\U+0130N ADI")
   ("T" "CLD-P2-ICT-YAZI" 119098.1 -96362.5 20.0 0 "ELEKTR\\U+0130K \\U+0130\\U+00C7 TES\\U+0130SAT PROJES\\U+0130")
   ("L" "CLD-P2-ICT-PAFTA" 118478.1 -96396.5 120978.1 -96396.5)
   ("T" "CLD-P2-ICT-YAZI" 118508.1 -96459.6 18.0 0 "YAPI SAH\\U+0130B\\U+0130")
   ("T" "CLD-P2-ICT-YAZI" 119098.1 -96459.6 20.0 0 "BROSCO \\U+0130THALAT \\U+0130HRACAT VE T\\U+0130CARET ANON\\U+0130M \\U+015E\\U+0130RKET\\U+0130")
   ("L" "CLD-P2-ICT-PAFTA" 118478.1 -96493.6 120978.1 -96493.6)
   ("T" "CLD-P2-ICT-YAZI" 118508.1 -96556.8 18.0 0 "ADRES")
   ("T" "CLD-P2-ICT-YAZI" 119098.1 -96556.8 20.0 0 "YUKARI MAHALLE / KEMALPA\\U+015EA / \\U+0130ZM\\U+0130R  -  Ada: ......  Parsel: 2")
   ("L" "CLD-P2-ICT-PAFTA" 118478.1 -96590.8 120978.1 -96590.8)
   ("T" "CLD-P2-ICT-YAZI" 118508.1 -96653.9 18.0 0 "PAFTA ADI")
   ("T" "CLD-P2-ICT-YAZI" 119098.1 -96653.9 20.0 0 "AYDINLATMA TES\\U+0130SATI PLANI - 1. KAT PLANI")
   ("L" "CLD-P2-ICT-PAFTA" 118478.1 -96687.9 120978.1 -96687.9)
   ("T" "CLD-P2-ICT-YAZI" 118508.1 -96751.1 18.0 0 "\\U+00D6L\\U+00C7EK / TAR\\U+0130H / PAFTA NO")
   ("T" "CLD-P2-ICT-YAZI" 119098.1 -96751.1 20.0 0 "1/100   |   19.10.2026   |   01-02")
   ("L" "CLD-P2-ICT-PAFTA" 118478.1 -96785.1 120978.1 -96785.1)
   ("T" "CLD-P2-ICT-YAZI" 118508.1 -96848.2 18.0 0 "PROJE M\\U+00DCELL\\U+0130F\\U+0130")
   ("T" "CLD-P2-ICT-YAZI" 119098.1 -96848.2 20.0 0 "Elektrik M\\U+00FChendisi - Ad\\U+0131 Soyad\\U+0131: ..............................")
   ("L" "CLD-P2-ICT-PAFTA" 118478.1 -96882.2 120978.1 -96882.2)
   ("T" "CLD-P2-ICT-YAZI" 118508.1 -96945.4 18.0 0 "ODA S\\U+0130C\\U+0130L / SMM NO")
   ("T" "CLD-P2-ICT-YAZI" 119098.1 -96945.4 20.0 0 "EMO Sicil No: ............   SMM Belge No: ............   \\U+0130mza: ............")
   ("L" "CLD-P2-ICT-PAFTA" 119068.1 -96979.4 119068.1 -96299.4)
   ("T" "CLD-P2-ICT-YAZI" 109741.2 -96439.4 70.0 0 "AYDINLATMA TES\\U+0130SATI PLANI")
   ("T" "CLD-P2-ICT-YAZI" 109741.2 -96579.4 40.0 0 "1. KAT PLANI  -  \\U+00D6: 1/100")
   ("T" "CLD-P2-ICT-YAZI" 109741.2 -96679.4 30.0 0 "Parsel 2  |  BROSCO \\U+0130THALAT \\U+0130HRACAT VE T\\U+0130CARET ANON\\U+0130M \\U+015E\\U+0130RKET\\U+0130")
   ("T" "CLD-P2-ICT-YAZI" 109741.2 -96759.4 26.0 0 "CLD - 19.10.2026 - mimari altl\\U+0131k: BROSCO 2 NOLU PARSEL M\\U+0130MAR\\U+0130.dwg")
   ("I" "CLD-P2-ICT-PANO" "CLD_S_TP" 116857.8 -88192.6 1.5711 2.5)
   ("T" "CLD-P2-ICT-PANO" 116907.8 -88132.6 30.0 0 "IDP-1K")
   ("I" "CLD-P2-ICT-AYDINLATMA" "CLD_S_DLB" 116701.6 -88296.6 0.0 2.5)
   ("I" "CLD-P2-ICT-AYDINLATMA" "CLD_S_DLB" 116632.6 -88237.3 0.0 2.5)
   ("I" "CLD-P2-ICT-AYDINLATMA" "CLD_S_DLB" 116820.4 -88279.5 0.0 2.5)
   ("I" "CLD-P2-ICT-AYDINLATMA" "CLD_S_DL" 116658.1 -88435.3 0.0 2.5)
   ("I" "CLD-P2-ICT-AYDINLATMA" "CLD_S_DL" 117096.4 -88551.1 0.0 2.5)
   ("I" "CLD-P2-ICT-AYDINLATMA" "CLD_S_DL" 116950.3 -88551.2 0.0 2.5)
   ("I" "CLD-P2-ICT-AYDINLATMA" "CLD_S_DL" 116804.2 -88551.2 0.0 2.5)
   ("I" "CLD-P2-ICT-AYDINLATMA" "CLD_S_DL" 116658.1 -88551.3 0.0 2.5)
   ("I" "CLD-P2-ICT-ACIL" "CLD_S_ACIL" 116766.1 -88435.3 0.0 2.5)
   ("I" "CLD-P2-ICT-AYDINLATMA" "CLD_S_DL" 117009.9 -87996.1 0.0 2.5)
   ("I" "CLD-P2-ICT-AYDINLATMA" "CLD_S_DL" 116913.1 -88001.8 0.0 2.5)
   ("I" "CLD-P2-ICT-AYDINLATMA" "CLD_S_DL" 116719.5 -88013.3 0.0 2.5)
   ("I" "CLD-P2-ICT-AYDINLATMA" "CLD_S_DL" 116821.3 -88092.5 0.0 2.5)
   ("I" "CLD-P2-ICT-AYDINLATMA" "CLD_S_DL" 116724.5 -88098.2 0.0 2.5)
   ("I" "CLD-P2-ICT-ACIL" "CLD_S_ACIL" 116757.0 -88055.8 0.0 2.5)
   ("I" "CLD-P2-ICT-ANAHTAR" "CLD_S_ANH1" 116664.6 -88316.2 1.5708 2.5)
   ("I" "CLD-P2-ICT-ANAHTAR" "CLD_S_ANH1" 116866.2 -88292.5 2.4818 2.5)
   ("I" "CLD-P2-ICT-ANAHTAR" "CLD_S_ANH1" 116859.6 -88362.1 -0.9916 2.5)
   ("I" "CLD-P2-ICT-ANAHTAR" "CLD_S_ANH1" 116850.2 -87925.8 -1.3862 2.5)
   ("P" "CLD-P2-ICT-LINYE-AYD" nil 0.0 ((116820.4 -88279.5) (116701.6 -88296.6) (116632.6 -88237.3) (116724.5 -88098.2) (116821.3 -88092.5) (117009.9 -87996.1) (116913.1 -88001.8) (116719.5 -88013.3) (116658.1 -88435.3) (116658.1 -88551.3)))
   ("P" "CLD-P2-ICT-LINYE-AYD" nil 0.0 ((116857.8 -88192.6) (116820.4 -88279.5)))
   ("T" "CLD-P2-ICT-YAZI" 116855.4 -88249.5 18.0 0 "IDP-1K/A1")
   ("P" "CLD-P2-ICT-LINYE-AYD" nil 0.0 ((116804.2 -88551.2) (116950.3 -88551.2) (117096.4 -88551.1)))
   ("P" "CLD-P2-ICT-LINYE-AYD" nil 0.0 ((116804.2 -88551.2) (116821.9 -88432.6)))
   ("P" "CLD-P2-ICT-LINYE-AYD" nil 0.0 ((116806.4 -88455.5) (116821.9 -88432.6) (116830.1 -88459.0)))
   ("T" "CLD-P2-ICT-YAZI" 116836.9 -88417.6 18.0 0 "IDP-1K/A2")
   ("P" "CLD-P2-ICT-LINYE-AYD" nil 0.0 ((116757.0 -88055.8) (116766.1 -88435.3)))
   ("P" "CLD-P2-ICT-LINYE-AYD" nil 0.0 ((116757.0 -88055.8) (116807.4 -88124.2)))
   ("P" "CLD-P2-ICT-LINYE-AYD" nil 0.0 ((116802.2 -88096.9) (116807.4 -88124.2) (116782.9 -88111.2)))
   ("T" "CLD-P2-ICT-YAZI" 116822.4 -88109.2 18.0 0 "IDP-1K/AC3")
   ("I" "CLD-P2-ICT-ALTLIK" "CLD_P2_MIMARI_ZK_V2" 122078.1 -96279.4 0.0 0.01)
   ("T" "CLD-P2-ICT-TABLO" 132159.8 -86202.9 26.0 0 "LEJANT")
   ("P" "CLD-P2-ICT-TABLO" T 0.0 ((132159.8 -86222.9) (133188.6 -86222.9) (133188.6 -86882.9) (132159.8 -86882.9)))
   ("I" "CLD-P2-ICT-TABLO" "CLD_S_PRIZ" 132279.8 -86264.9 0.0 1.733)
   ("T" "CLD-P2-ICT-TABLO" 132399.8 -86264.9 20.0 7 "Toprakl\\U+0131 priz 16 A (h=40 cm, tezgah h=110 cm)")
   ("I" "CLD-P2-ICT-TABLO" "CLD_S_PRIZU" 132279.8 -86328.9 0.0 1.733)
   ("T" "CLD-P2-ICT-TABLO" 132399.8 -86328.9 20.0 7 "Bilgisayar prizi (ayr\\U+0131 linye, UPS haz\\U+0131rl\\U+0131\\U+011F\\U+0131)")
   ("I" "CLD-P2-ICT-TABLO" "CLD_S_PRIZE" 132279.8 -86392.9 0.0 1.733)
   ("T" "CLD-P2-ICT-TABLO" 132399.8 -86392.9 20.0 7 "Etanj priz IP44")
   ("I" "CLD-P2-ICT-TABLO" "CLD_S_PGRUP" 132279.8 -86456.9 0.0 1.04)))))
(defun cld:ops-p2_elektrik_ic_tesisat-4 () (cld:play (quote (
   ("T" "CLD-P2-ICT-TABLO" 132399.8 -86456.9 20.0 7 "End\\U+00FCstriyel priz grubu CEE 32A+16A+2x16A (i\\U+00E7 koruma, h=150 cm)")
   ("I" "CLD-P2-ICT-TABLO" "CLD_S_CK_ISITICI" 132279.8 -86520.9 0.0 1.733)
   ("T" "CLD-P2-ICT-TABLO" 132399.8 -86520.9 20.0 7 "Ani su \\U+0131s\\U+0131t\\U+0131c\\U+0131 \\U+00E7\\U+0131k\\U+0131\\U+015F\\U+0131 (IS) - ayr\\U+0131 linye")
   ("I" "CLD-P2-ICT-TABLO" "CLD_S_CK_TERMOSIFON" 132279.8 -86584.9 0.0 1.733)
   ("T" "CLD-P2-ICT-TABLO" 132399.8 -86584.9 20.0 7 "Elektrikli termosifon \\U+00E7\\U+0131k\\U+0131\\U+015F\\U+0131 (TS) - ayr\\U+0131 linye")
   ("I" "CLD-P2-ICT-TABLO" "CLD_S_CK_BULASIK" 132279.8 -86648.9 0.0 1.733)
   ("T" "CLD-P2-ICT-TABLO" 132399.8 -86648.9 20.0 7 "Bula\\U+015F\\U+0131k makinesi \\U+00E7\\U+0131k\\U+0131\\U+015F\\U+0131 (B) - ayr\\U+0131 linye")
   ("I" "CLD-P2-ICT-TABLO" "CLD_S_CK_ASPIRATOR" 132279.8 -86712.9 0.0 1.733)
   ("T" "CLD-P2-ICT-TABLO" 132399.8 -86712.9 20.0 7 "Havaland\\U+0131rma cihaz\\U+0131 / aspirat\\U+00F6r \\U+00E7\\U+0131k\\U+0131\\U+015F\\U+0131 (A) - ayr\\U+0131 linye")
   ("I" "CLD-P2-ICT-TABLO" "CLD_S_TP" 132279.8 -86776.9 0.0 1.04)
   ("T" "CLD-P2-ICT-TABLO" 132399.8 -86776.9 20.0 7 "Tali da\\U+011F\\U+0131t\\U+0131m panosu (UTP / \\U+0130DP)")
   ("P" "CLD-P2-ICT-LINYE-PRIZ" nil 0.0 ((132179.8 -86840.9) (132379.8 -86840.9)))
   ("T" "CLD-P2-ICT-TABLO" 132399.8 -86840.9 20.0 7 "Priz / kuvvet linyesi, ok: panoya d\\U+00F6n\\U+00FC\\U+015F")
   ("P" "CLD-P2-ICT-PAFTA" nil 6.0 ((132009.8 -96299.4) (132009.8 -86052.9)))
   ("P" "CLD-P2-ICT-PAFTA" T 10.0 ((121978.1 -96979.4) (133438.6 -96979.4) (133438.6 -86052.9) (121978.1 -86052.9)))
   ("P" "CLD-P2-ICT-PAFTA" nil 6.0 ((121978.1 -96299.4) (133438.6 -96299.4)))
   ("P" "CLD-P2-ICT-PAFTA" T 6.0 ((130938.6 -96979.4) (133438.6 -96979.4) (133438.6 -96299.4) (130938.6 -96299.4)))
   ("T" "CLD-P2-ICT-YAZI" 130968.6 -96362.5 18.0 0 "\\U+0130\\U+015E\\U+0130N ADI")
   ("T" "CLD-P2-ICT-YAZI" 131558.6 -96362.5 20.0 0 "ELEKTR\\U+0130K \\U+0130\\U+00C7 TES\\U+0130SAT PROJES\\U+0130")
   ("L" "CLD-P2-ICT-PAFTA" 130938.6 -96396.5 133438.6 -96396.5)
   ("T" "CLD-P2-ICT-YAZI" 130968.6 -96459.6 18.0 0 "YAPI SAH\\U+0130B\\U+0130")
   ("T" "CLD-P2-ICT-YAZI" 131558.6 -96459.6 20.0 0 "BROSCO \\U+0130THALAT \\U+0130HRACAT VE T\\U+0130CARET ANON\\U+0130M \\U+015E\\U+0130RKET\\U+0130")
   ("L" "CLD-P2-ICT-PAFTA" 130938.6 -96493.6 133438.6 -96493.6)
   ("T" "CLD-P2-ICT-YAZI" 130968.6 -96556.8 18.0 0 "ADRES")
   ("T" "CLD-P2-ICT-YAZI" 131558.6 -96556.8 20.0 0 "YUKARI MAHALLE / KEMALPA\\U+015EA / \\U+0130ZM\\U+0130R  -  Ada: ......  Parsel: 2")
   ("L" "CLD-P2-ICT-PAFTA" 130938.6 -96590.8 133438.6 -96590.8)
   ("T" "CLD-P2-ICT-YAZI" 130968.6 -96653.9 18.0 0 "PAFTA ADI")
   ("T" "CLD-P2-ICT-YAZI" 131558.6 -96653.9 20.0 0 "PR\\U+0130Z VE KUVVET TES\\U+0130SATI PLANI - ZEM\\U+0130N KAT PLANI")
   ("L" "CLD-P2-ICT-PAFTA" 130938.6 -96687.9 133438.6 -96687.9)
   ("T" "CLD-P2-ICT-YAZI" 130968.6 -96751.1 18.0 0 "\\U+00D6L\\U+00C7EK / TAR\\U+0130H / PAFTA NO")
   ("T" "CLD-P2-ICT-YAZI" 131558.6 -96751.1 20.0 0 "1/100   |   19.10.2026   |   01-03")
   ("L" "CLD-P2-ICT-PAFTA" 130938.6 -96785.1 133438.6 -96785.1)
   ("T" "CLD-P2-ICT-YAZI" 130968.6 -96848.2 18.0 0 "PROJE M\\U+00DCELL\\U+0130F\\U+0130")
   ("T" "CLD-P2-ICT-YAZI" 131558.6 -96848.2 20.0 0 "Elektrik M\\U+00FChendisi - Ad\\U+0131 Soyad\\U+0131: ..............................")
   ("L" "CLD-P2-ICT-PAFTA" 130938.6 -96882.2 133438.6 -96882.2)
   ("T" "CLD-P2-ICT-YAZI" 130968.6 -96945.4 18.0 0 "ODA S\\U+0130C\\U+0130L / SMM NO")
   ("T" "CLD-P2-ICT-YAZI" 131558.6 -96945.4 20.0 0 "EMO Sicil No: ............   SMM Belge No: ............   \\U+0130mza: ............")
   ("L" "CLD-P2-ICT-PAFTA" 131528.6 -96979.4 131528.6 -96299.4)
   ("T" "CLD-P2-ICT-YAZI" 122078.1 -96439.4 70.0 0 "PR\\U+0130Z VE KUVVET TES\\U+0130SATI PLANI")
   ("T" "CLD-P2-ICT-YAZI" 122078.1 -96579.4 40.0 0 "ZEM\\U+0130N KAT PLANI  -  \\U+00D6: 1/100")
   ("T" "CLD-P2-ICT-YAZI" 122078.1 -96679.4 30.0 0 "Parsel 2  |  BROSCO \\U+0130THALAT \\U+0130HRACAT VE T\\U+0130CARET ANON\\U+0130M \\U+015E\\U+0130RKET\\U+0130")
   ("T" "CLD-P2-ICT-YAZI" 122078.1 -96759.4 26.0 0 "CLD - 19.10.2026 - mimari altl\\U+0131k: BROSCO 2 NOLU PARSEL M\\U+0130MAR\\U+0130.dwg")
   ("I" "CLD-P2-ICT-PANO" "CLD_S_TP" 126677.6 -90462.2 1.3406 2.5)
   ("T" "CLD-P2-ICT-PANO" 126727.6 -90402.2 30.0 0 "UTP-1")
   ("I" "CLD-P2-ICT-PANO" "CLD_S_TP" 130960.4 -90575.0 3.1415 2.5)
   ("T" "CLD-P2-ICT-PANO" 131010.4 -90515.0 30.0 0 "UTP-2")
   ("I" "CLD-P2-ICT-PANO" "CLD_S_TP" 129212.1 -88105.1 3.1416 2.5)
   ("T" "CLD-P2-ICT-PANO" 129262.1 -88045.1 30.0 0 "IDP-ZK")
   ("I" "CLD-P2-ICT-PRIZ" "CLD_S_PRIZE" 129340.8 -88497.9 3.1416 2.5)
   ("I" "CLD-P2-ICT-PRIZ" "CLD_S_PRIZE" 129486.6 -88480.7 3.1416 2.5)
   ("I" "CLD-P2-ICT-PRIZ" "CLD_S_PRIZE" 129388.1 -88498.2 0.0 2.5)
   ("I" "CLD-P2-ICT-PRIZ" "CLD_S_PRIZE" 129492.4 -88317.6 3.1416 2.5)
   ("I" "CLD-P2-ICT-PRIZ" "CLD_S_PRIZE" 129492.4 -88095.8 3.1416 2.5)
   ("I" "CLD-P2-ICT-OZEL-CIKIS" "CLD_S_CK_ASPIRATOR" 129044.3 -88214.0 0.0 2.5)
   ("I" "CLD-P2-ICT-OZEL-CIKIS" "CLD_S_PGRUP" 129013.3 -91630.5 0.6202 1.6)
   ("I" "CLD-P2-ICT-OZEL-CIKIS" "CLD_S_PGRUP" 130305.1 -93439.1 0.6202 1.6)
   ("I" "CLD-P2-ICT-OZEL-CIKIS" "CLD_S_PGRUP" 130980.3 -92980.7 3.1415 1.6)
   ("I" "CLD-P2-ICT-OZEL-CIKIS" "CLD_S_PGRUP" 130980.4 -90281.9 3.1415 1.6)
   ("I" "CLD-P2-ICT-OZEL-CIKIS" "CLD_S_PGRUP" 130980.6 -88257.9 3.1415 1.6)
   ("I" "CLD-P2-ICT-OZEL-CIKIS" "CLD_S_PGRUP" 129699.8 -88187.6 0.0 1.6)
   ("I" "CLD-P2-ICT-OZEL-CIKIS" "CLD_S_PGRUP" 129051.8 -89886.1 0.0 1.6)
   ("I" "CLD-P2-ICT-OZEL-CIKIS" "CLD_S_PGRUP" 124114.6 -89882.1 1.3406 1.6)
   ("I" "CLD-P2-ICT-OZEL-CIKIS" "CLD_S_PGRUP" 126261.2 -90385.1 1.3406 1.6)
   ("I" "CLD-P2-ICT-OZEL-CIKIS" "CLD_S_PGRUP" 128668.8 -91003.6 1.5708 1.6)
   ("I" "CLD-P2-ICT-OZEL-CIKIS" "CLD_S_PGRUP" 129001.8 -89577.6 3.1416 1.6)
   ("I" "CLD-P2-ICT-OZEL-CIKIS" "CLD_S_PGRUP" 127942.6 -88171.8 -1.3862 1.6)
   ("I" "CLD-P2-ICT-OZEL-CIKIS" "CLD_S_PGRUP" 126413.8 -88540.0 -1.3211 1.6)
   ("I" "CLD-P2-ICT-OZEL-CIKIS" "CLD_S_PGRUP" 124275.1 -89085.3 -1.3211 1.6)
   ("I" "CLD-P2-ICT-OZEL-CIKIS" "CLD_S_CK_TERMOSIFON" 129120.3 -88490.4 3.1416 2.5)
   ("P" "CLD-P2-ICT-LINYE-PRIZ" nil 0.0 ((129492.4 -88095.8) (129492.4 -88317.6) (129340.8 -88497.9) (129388.1 -88498.2) (129486.6 -88480.7)))
   ("P" "CLD-P2-ICT-LINYE-PRIZ" nil 0.0 ((129492.4 -88095.8) (129372.4 -88099.8)))
   ("P" "CLD-P2-ICT-LINYE-PRIZ" nil 0.0 ((129397.8 -88111.0) (129372.4 -88099.8) (129397.0 -88087.0)))
   ("T" "CLD-P2-ICT-YAZI" 129387.4 -88084.8 18.0 0 "IDP-ZK/P3")
   ("P" "CLD-P2-ICT-LINYE-PRIZ" nil 0.0 ((129044.3 -88214.0) (129128.2 -88159.5)))
   ("P" "CLD-P2-ICT-LINYE-PRIZ" nil 0.0 ((129100.7 -88163.1) (129128.2 -88159.5) (129113.8 -88183.2)))
   ("T" "CLD-P2-ICT-YAZI" 129143.2 -88144.5 18.0 0 "IDP-ZK/K4")
   ("P" "CLD-P2-ICT-LINYE-PRIZ" nil 0.0 ((129120.3 -88490.4) (129148.1 -88373.6)))
   ("P" "CLD-P2-ICT-LINYE-PRIZ" nil 0.0 ((129130.6 -88395.2) (129148.1 -88373.6) (129154.0 -88400.7)))
   ("T" "CLD-P2-ICT-YAZI" 129163.1 -88358.6 18.0 0 "IDP-ZK/K5")
   ("P" "CLD-P2-ICT-LINYE-PRIZ" nil 0.0 ((129013.3 -91630.5) (129118.8 -91573.3)))
   ("P" "CLD-P2-ICT-LINYE-PRIZ" nil 0.0 ((129091.1 -91574.7) (129118.8 -91573.3) (129102.5 -91595.8)))
   ("T" "CLD-P2-ICT-YAZI" 129133.8 -91558.3 18.0 0 "UTP-2/G9")
   ("P" "CLD-P2-ICT-LINYE-PRIZ" nil 0.0 ((130305.1 -93439.1) (130331.9 -93322.2)))
   ("P" "CLD-P2-ICT-LINYE-PRIZ" nil 0.0 ((130314.6 -93343.9) (130331.9 -93322.2) (130338.0 -93349.2)))
   ("T" "CLD-P2-ICT-YAZI" 130346.9 -93307.2 18.0 0 "UTP-2/G10")
   ("P" "CLD-P2-ICT-LINYE-PRIZ" nil 0.0 ((130980.3 -92980.7) (130979.3 -92860.7)))
   ("P" "CLD-P2-ICT-LINYE-PRIZ" nil 0.0 ((130967.5 -92885.8) (130979.3 -92860.7) (130991.5 -92885.6)))
   ("T" "CLD-P2-ICT-YAZI" 130994.3 -92845.7 18.0 0 "UTP-2/G11")
   ("P" "CLD-P2-ICT-LINYE-PRIZ" nil 0.0 ((130980.4 -90281.9) (130972.3 -90401.7)))
   ("P" "CLD-P2-ICT-LINYE-PRIZ" nil 0.0 ((130985.9 -90377.5) (130972.3 -90401.7) (130962.0 -90375.9)))
   ("T" "CLD-P2-ICT-YAZI" 130987.3 -90386.7 18.0 0 "UTP-2/G12")
   ("P" "CLD-P2-ICT-LINYE-PRIZ" nil 0.0 ((130980.6 -88257.9) (130979.5 -88377.9)))
   ("P" "CLD-P2-ICT-LINYE-PRIZ" nil 0.0 ((130991.7 -88353.0) (130979.5 -88377.9) (130967.7 -88352.8)))
   ("T" "CLD-P2-ICT-YAZI" 130994.5 -88362.9 18.0 0 "UTP-2/G13")
   ("P" "CLD-P2-ICT-LINYE-PRIZ" nil 0.0 ((129699.8 -88187.6) (129755.9 -88293.7)))
   ("P" "CLD-P2-ICT-LINYE-PRIZ" nil 0.0 ((129754.8 -88266.0) (129755.9 -88293.7) (129733.6 -88277.2)))
   ("T" "CLD-P2-ICT-YAZI" 129770.9 -88278.7 18.0 0 "UTP-2/G14")
   ("P" "CLD-P2-ICT-LINYE-PRIZ" nil 0.0 ((129051.8 -89886.1) (129164.6 -89926.9)))
   ("P" "CLD-P2-ICT-LINYE-PRIZ" nil 0.0 ((129145.2 -89907.1) (129164.6 -89926.9) (129137.0 -89929.7)))
   ("T" "CLD-P2-ICT-YAZI" 129179.6 -89911.9 18.0 0 "UTP-2/G15")
   ("P" "CLD-P2-ICT-LINYE-PRIZ" nil 0.0 ((124114.6 -89882.1) (124231.6 -89908.6)))
   ("P" "CLD-P2-ICT-LINYE-PRIZ" nil 0.0 ((124209.9 -89891.3) (124231.6 -89908.6) (124204.6 -89914.7)))
   ("T" "CLD-P2-ICT-YAZI" 124246.6 -89893.6 18.0 0 "UTP-1/G9")
   ("P" "CLD-P2-ICT-LINYE-PRIZ" nil 0.0 ((126261.2 -90385.1) (126379.2 -90407.0)))
   ("P" "CLD-P2-ICT-LINYE-PRIZ" nil 0.0 ((126356.8 -90390.6) (126379.2 -90407.0) (126352.4 -90414.2)))
   ("T" "CLD-P2-ICT-YAZI" 126394.2 -90392.0 18.0 0 "UTP-1/G10")
   ("P" "CLD-P2-ICT-LINYE-PRIZ" nil 0.0 ((128668.8 -91003.6) (128553.0 -90972.1)))
   ("P" "CLD-P2-ICT-LINYE-PRIZ" nil 0.0 ((128574.0 -90990.2) (128553.0 -90972.1) (128580.3 -90967.1)))
   ("T" "CLD-P2-ICT-YAZI" 128568.0 -90957.1 18.0 0 "UTP-1/G11")
   ("P" "CLD-P2-ICT-LINYE-PRIZ" nil 0.0 ((129001.8 -89577.6) (128889.6 -89620.3)))
   ("P" "CLD-P2-ICT-LINYE-PRIZ" nil 0.0 ((128917.2 -89622.6) (128889.6 -89620.3) (128908.7 -89600.2)))
   ("T" "CLD-P2-ICT-YAZI" 128904.6 -89605.3 18.0 0 "UTP-1/G12")
   ("P" "CLD-P2-ICT-LINYE-PRIZ" nil 0.0 ((127942.6 -88171.8) (127884.6 -88276.8)))
   ("P" "CLD-P2-ICT-LINYE-PRIZ" nil 0.0 ((127907.2 -88260.7) (127884.6 -88276.8) (127886.1 -88249.1)))
   ("T" "CLD-P2-ICT-YAZI" 127899.6 -88261.8 18.0 0 "UTP-1/G13")
   ("P" "CLD-P2-ICT-LINYE-PRIZ" nil 0.0 ((126413.8 -88540.0) (126430.1 -88658.9)))
   ("P" "CLD-P2-ICT-LINYE-PRIZ" nil 0.0 ((126438.6 -88632.5) (126430.1 -88658.9) (126414.8 -88635.7)))
   ("T" "CLD-P2-ICT-YAZI" 126445.1 -88643.9 18.0 0 "UTP-1/G14")
   ("P" "CLD-P2-ICT-LINYE-PRIZ" nil 0.0 ((124275.1 -89085.3) (124379.2 -89145.0)))
   ("P" "CLD-P2-ICT-LINYE-PRIZ" nil 0.0 ((124363.5 -89122.2) (124379.2 -89145.0) (124351.6 -89143.0)))))))
(defun cld:ops-p2_elektrik_ic_tesisat-5 () (cld:play (quote (
   ("T" "CLD-P2-ICT-YAZI" 124394.2 -89130.0 18.0 0 "UTP-1/G15")
   ("I" "CLD-P2-ICT-ALTLIK" "CLD_P2_MIMARI_1K_V2" 134538.6 -96279.4 0.0 0.01)
   ("T" "CLD-P2-ICT-TABLO" 144459.5 -86202.9 26.0 0 "LEJANT")
   ("P" "CLD-P2-ICT-TABLO" T 0.0 ((144459.5 -86222.9) (145488.3 -86222.9) (145488.3 -86882.9) (144459.5 -86882.9)))
   ("I" "CLD-P2-ICT-TABLO" "CLD_S_PRIZ" 144579.5 -86264.9 0.0 1.733)
   ("T" "CLD-P2-ICT-TABLO" 144699.5 -86264.9 20.0 7 "Toprakl\\U+0131 priz 16 A (h=40 cm, tezgah h=110 cm)")
   ("I" "CLD-P2-ICT-TABLO" "CLD_S_PRIZU" 144579.5 -86328.9 0.0 1.733)
   ("T" "CLD-P2-ICT-TABLO" 144699.5 -86328.9 20.0 7 "Bilgisayar prizi (ayr\\U+0131 linye, UPS haz\\U+0131rl\\U+0131\\U+011F\\U+0131)")
   ("I" "CLD-P2-ICT-TABLO" "CLD_S_PRIZE" 144579.5 -86392.9 0.0 1.733)
   ("T" "CLD-P2-ICT-TABLO" 144699.5 -86392.9 20.0 7 "Etanj priz IP44")
   ("I" "CLD-P2-ICT-TABLO" "CLD_S_PGRUP" 144579.5 -86456.9 0.0 1.04)
   ("T" "CLD-P2-ICT-TABLO" 144699.5 -86456.9 20.0 7 "End\\U+00FCstriyel priz grubu CEE 32A+16A+2x16A (i\\U+00E7 koruma, h=150 cm)")
   ("I" "CLD-P2-ICT-TABLO" "CLD_S_CK_ISITICI" 144579.5 -86520.9 0.0 1.733)
   ("T" "CLD-P2-ICT-TABLO" 144699.5 -86520.9 20.0 7 "Ani su \\U+0131s\\U+0131t\\U+0131c\\U+0131 \\U+00E7\\U+0131k\\U+0131\\U+015F\\U+0131 (IS) - ayr\\U+0131 linye")
   ("I" "CLD-P2-ICT-TABLO" "CLD_S_CK_TERMOSIFON" 144579.5 -86584.9 0.0 1.733)
   ("T" "CLD-P2-ICT-TABLO" 144699.5 -86584.9 20.0 7 "Elektrikli termosifon \\U+00E7\\U+0131k\\U+0131\\U+015F\\U+0131 (TS) - ayr\\U+0131 linye")
   ("I" "CLD-P2-ICT-TABLO" "CLD_S_CK_BULASIK" 144579.5 -86648.9 0.0 1.733)
   ("T" "CLD-P2-ICT-TABLO" 144699.5 -86648.9 20.0 7 "Bula\\U+015F\\U+0131k makinesi \\U+00E7\\U+0131k\\U+0131\\U+015F\\U+0131 (B) - ayr\\U+0131 linye")
   ("I" "CLD-P2-ICT-TABLO" "CLD_S_CK_ASPIRATOR" 144579.5 -86712.9 0.0 1.733)
   ("T" "CLD-P2-ICT-TABLO" 144699.5 -86712.9 20.0 7 "Havaland\\U+0131rma cihaz\\U+0131 / aspirat\\U+00F6r \\U+00E7\\U+0131k\\U+0131\\U+015F\\U+0131 (A) - ayr\\U+0131 linye")
   ("I" "CLD-P2-ICT-TABLO" "CLD_S_TP" 144579.5 -86776.9 0.0 1.04)
   ("T" "CLD-P2-ICT-TABLO" 144699.5 -86776.9 20.0 7 "Tali da\\U+011F\\U+0131t\\U+0131m panosu (UTP / \\U+0130DP)")
   ("P" "CLD-P2-ICT-LINYE-PRIZ" nil 0.0 ((144479.5 -86840.9) (144679.5 -86840.9)))
   ("T" "CLD-P2-ICT-TABLO" 144699.5 -86840.9 20.0 7 "Priz / kuvvet linyesi, ok: panoya d\\U+00F6n\\U+00FC\\U+015F")
   ("P" "CLD-P2-ICT-PAFTA" nil 6.0 ((144309.5 -96299.4) (144309.5 -86052.9)))
   ("P" "CLD-P2-ICT-PAFTA" T 10.0 ((134438.6 -96979.4) (145738.3 -96979.4) (145738.3 -86052.9) (134438.6 -86052.9)))
   ("P" "CLD-P2-ICT-PAFTA" nil 6.0 ((134438.6 -96299.4) (145738.3 -96299.4)))
   ("P" "CLD-P2-ICT-PAFTA" T 6.0 ((143238.3 -96979.4) (145738.3 -96979.4) (145738.3 -96299.4) (143238.3 -96299.4)))
   ("T" "CLD-P2-ICT-YAZI" 143268.3 -96362.5 18.0 0 "\\U+0130\\U+015E\\U+0130N ADI")
   ("T" "CLD-P2-ICT-YAZI" 143858.3 -96362.5 20.0 0 "ELEKTR\\U+0130K \\U+0130\\U+00C7 TES\\U+0130SAT PROJES\\U+0130")
   ("L" "CLD-P2-ICT-PAFTA" 143238.3 -96396.5 145738.3 -96396.5)
   ("T" "CLD-P2-ICT-YAZI" 143268.3 -96459.6 18.0 0 "YAPI SAH\\U+0130B\\U+0130")
   ("T" "CLD-P2-ICT-YAZI" 143858.3 -96459.6 20.0 0 "BROSCO \\U+0130THALAT \\U+0130HRACAT VE T\\U+0130CARET ANON\\U+0130M \\U+015E\\U+0130RKET\\U+0130")
   ("L" "CLD-P2-ICT-PAFTA" 143238.3 -96493.6 145738.3 -96493.6)
   ("T" "CLD-P2-ICT-YAZI" 143268.3 -96556.8 18.0 0 "ADRES")
   ("T" "CLD-P2-ICT-YAZI" 143858.3 -96556.8 20.0 0 "YUKARI MAHALLE / KEMALPA\\U+015EA / \\U+0130ZM\\U+0130R  -  Ada: ......  Parsel: 2")
   ("L" "CLD-P2-ICT-PAFTA" 143238.3 -96590.8 145738.3 -96590.8)
   ("T" "CLD-P2-ICT-YAZI" 143268.3 -96653.9 18.0 0 "PAFTA ADI")
   ("T" "CLD-P2-ICT-YAZI" 143858.3 -96653.9 20.0 0 "PR\\U+0130Z VE KUVVET TES\\U+0130SATI PLANI - 1. KAT PLANI")
   ("L" "CLD-P2-ICT-PAFTA" 143238.3 -96687.9 145738.3 -96687.9)
   ("T" "CLD-P2-ICT-YAZI" 143268.3 -96751.1 18.0 0 "\\U+00D6L\\U+00C7EK / TAR\\U+0130H / PAFTA NO")
   ("T" "CLD-P2-ICT-YAZI" 143858.3 -96751.1 20.0 0 "1/100   |   19.10.2026   |   01-04")
   ("L" "CLD-P2-ICT-PAFTA" 143238.3 -96785.1 145738.3 -96785.1)
   ("T" "CLD-P2-ICT-YAZI" 143268.3 -96848.2 18.0 0 "PROJE M\\U+00DCELL\\U+0130F\\U+0130")
   ("T" "CLD-P2-ICT-YAZI" 143858.3 -96848.2 20.0 0 "Elektrik M\\U+00FChendisi - Ad\\U+0131 Soyad\\U+0131: ..............................")
   ("L" "CLD-P2-ICT-PAFTA" 143238.3 -96882.2 145738.3 -96882.2)
   ("T" "CLD-P2-ICT-YAZI" 143268.3 -96945.4 18.0 0 "ODA S\\U+0130C\\U+0130L / SMM NO")
   ("T" "CLD-P2-ICT-YAZI" 143858.3 -96945.4 20.0 0 "EMO Sicil No: ............   SMM Belge No: ............   \\U+0130mza: ............")
   ("L" "CLD-P2-ICT-PAFTA" 143828.3 -96979.4 143828.3 -96299.4)
   ("T" "CLD-P2-ICT-YAZI" 134538.6 -96439.4 70.0 0 "PR\\U+0130Z VE KUVVET TES\\U+0130SATI PLANI")
   ("T" "CLD-P2-ICT-YAZI" 134538.6 -96579.4 40.0 0 "1. KAT PLANI  -  \\U+00D6: 1/100")
   ("T" "CLD-P2-ICT-YAZI" 134538.6 -96679.4 30.0 0 "Parsel 2  |  BROSCO \\U+0130THALAT \\U+0130HRACAT VE T\\U+0130CARET ANON\\U+0130M \\U+015E\\U+0130RKET\\U+0130")
   ("T" "CLD-P2-ICT-YAZI" 134538.6 -96759.4 26.0 0 "CLD - 19.10.2026 - mimari altl\\U+0131k: BROSCO 2 NOLU PARSEL M\\U+0130MAR\\U+0130.dwg")
   ("I" "CLD-P2-ICT-PANO" "CLD_S_TP" 141655.2 -88192.6 1.5711 2.5)
   ("T" "CLD-P2-ICT-PANO" 141705.2 -88132.6 30.0 0 "IDP-1K")
   ("I" "CLD-P2-ICT-PRIZ" "CLD_S_PRIZE" 141407.6 -88265.8 0.0 2.5)
   ("I" "CLD-P2-ICT-OZEL-CIKIS" "CLD_S_CK_ISITICI" 141443.3 -88314.2 1.5708 2.5)
   ("I" "CLD-P2-ICT-PRIZ" "CLD_S_PRIZE" 141682.6 -88231.6 -1.5705 2.5)
   ("I" "CLD-P2-ICT-OZEL-CIKIS" "CLD_S_CK_ISITICI" 141631.7 -88231.6 -1.5705 2.5)
   ("I" "CLD-P2-ICT-PRIZ" "CLD_S_PRIZ" 141394.5 -88555.0 0.0 2.5)
   ("I" "CLD-P2-ICT-PRIZ" "CLD_S_PRIZ" 141592.9 -88351.5 4.7124 2.5)
   ("I" "CLD-P2-ICT-PRIZ" "CLD_S_PRIZ" 141933.0 -88063.1 3.1416 2.5)
   ("I" "CLD-P2-ICT-PRIZ" "CLD_S_PRIZ" 141514.7 -87952.7 -1.3862 2.5)
   ("P" "CLD-P2-ICT-LINYE-PRIZ" nil 0.0 ((141682.6 -88231.6) (141592.9 -88351.5) (141394.5 -88555.0) (141407.6 -88265.8) (141514.7 -87952.7) (141933.0 -88063.1)))
   ("P" "CLD-P2-ICT-LINYE-PRIZ" nil 0.0 ((141655.2 -88192.6) (141682.6 -88231.6)))
   ("T" "CLD-P2-ICT-YAZI" 141717.6 -88201.6 18.0 0 "IDP-1K/P4")
   ("P" "CLD-P2-ICT-LINYE-PRIZ" nil 0.0 ((141443.3 -88314.2) (141547.4 -88254.5)))
   ("P" "CLD-P2-ICT-LINYE-PRIZ" nil 0.0 ((141519.7 -88256.5) (141547.4 -88254.5) (141531.7 -88277.3)))
   ("T" "CLD-P2-ICT-YAZI" 141562.4 -88239.5 18.0 0 "IDP-1K/K5")
   ("P" "CLD-P2-ICT-LINYE-PRIZ" nil 0.0 ((141655.2 -88192.6) (141631.7 -88231.6)))
   ("T" "CLD-P2-ICT-YAZI" 141666.7 -88201.6 18.0 0 "IDP-1K/K6")
   ("P" "CLD-P2-ICT-LINYE-PRIZ" nil 0.0 ((141519.4 -88055.8) (141528.5 -88435.3)))
   ("P" "CLD-P2-ICT-LINYE-PRIZ" nil 0.0 ((141519.4 -88055.8) (141587.3 -88124.2)))
   ("P" "CLD-P2-ICT-LINYE-PRIZ" nil 0.0 ((141578.2 -88098.0) (141587.3 -88124.2) (141561.2 -88114.9)))
   ("T" "CLD-P2-ICT-YAZI" 141602.3 -88109.2 18.0 0 "IDP-1K/K7")
   ("T" "CLD-P2-ICT-TABLO" 146838.3 -86302.9 32.5 0 "LEJANT")
   ("P" "CLD-P2-ICT-TABLO" T 0.0 ((146838.3 -86327.9) (148170.8 -86327.9) (148170.8 -88112.9) (146838.3 -88112.9)))
   ("I" "CLD-P2-ICT-TABLO" "CLD_S_HB" 146988.3 -86380.4 0.0 1.083)
   ("T" "CLD-P2-ICT-TABLO" 147138.3 -86380.4 25.0 7 "LED y\\U+00FCksek tavan (highbay) armat\\U+00FCr\\U+00FC 150 W, 21.000 lm, IP65")
   ("I" "CLD-P2-ICT-TABLO" "CLD_S_PNL" 146988.3 -86460.4 0.0 1.0)
   ("T" "CLD-P2-ICT-TABLO" 147138.3 -86460.4 25.0 7 "LED panel armat\\U+00FCr 60x60, 36 W, 3.600 lm, UGR<19")
   ("I" "CLD-P2-ICT-TABLO" "CLD_S_DL" 146988.3 -86540.4 0.0 2.031)
   ("T" "CLD-P2-ICT-TABLO" 147138.3 -86540.4 25.0 7 "LED downlight 18 W, 1.800 lm, IP20")
   ("I" "CLD-P2-ICT-TABLO" "CLD_S_DLB" 146988.3 -86620.4 0.0 2.031)
   ("T" "CLD-P2-ICT-TABLO" 147138.3 -86620.4 25.0 7 "LED downlight 12 W, 1.200 lm, IP44 (\\U+0131slak hacim)")
   ("I" "CLD-P2-ICT-TABLO" "CLD_S_ETJ" 146988.3 -86700.4 0.0 0.542)
   ("T" "CLD-P2-ICT-TABLO" 147138.3 -86700.4 25.0 7 "LED etanj armat\\U+00FCr 36 W, 4.000 lm, IP65")
   ("I" "CLD-P2-ICT-TABLO" "CLD_S_ACIL" 146988.3 -86780.4 0.0 2.031)
   ("T" "CLD-P2-ICT-TABLO" 147138.3 -86780.4 25.0 7 "LED acil ayd\\U+0131nlatma armat\\U+00FCr\\U+00FC 3 W, 3 saat, s\\U+00FCrekli/s\\U+00FCrekli olmayan")
   ("I" "CLD-P2-ICT-TABLO" "CLD_S_EXIT" 146988.3 -86860.4 0.0 1.625)
   ("T" "CLD-P2-ICT-TABLO" 147138.3 -86860.4 25.0 7 "LED \\U+00E7\\U+0131k\\U+0131\\U+015F/y\\U+00F6nlendirme armat\\U+00FCr\\U+00FC 3 W, 3 saat")
   ("T" "CLD-P2-ICT-TABLO" 147138.3 -86940.4 25.0 7 "AK: 3 saat acil kitli armat\\U+00FCr (s\\U+00FCrekli faz ile beslenir)")
   ("I" "CLD-P2-ICT-TABLO" "CLD_S_ANH1" 146988.3 -87020.4 0.0 2.167)
   ("T" "CLD-P2-ICT-TABLO" 147138.3 -87020.4 25.0 7 "Adi anahtar (h=110 cm)")
   ("I" "CLD-P2-ICT-TABLO" "CLD_S_ANH2" 146988.3 -87100.4 0.0 2.167)
   ("T" "CLD-P2-ICT-TABLO" 147138.3 -87100.4 25.0 7 "Kom\\U+00FCtat\\U+00F6r anahtar")
   ("I" "CLD-P2-ICT-TABLO" "CLD_S_VAV" 146988.3 -87180.4 0.0 1.625)
   ("T" "CLD-P2-ICT-TABLO" 147138.3 -87180.4 25.0 7 "Vavien anahtar")
   ("I" "CLD-P2-ICT-TABLO" "CLD_S_TP" 146988.3 -87260.4 0.0 1.3)
   ("T" "CLD-P2-ICT-TABLO" 147138.3 -87260.4 25.0 7 "Tali da\\U+011F\\U+0131t\\U+0131m panosu (UTP / \\U+0130DP)")
   ("P" "CLD-P2-ICT-LINYE-AYD" nil 0.0 ((146863.3 -87340.4) (147113.3 -87340.4)))
   ("T" "CLD-P2-ICT-TABLO" 147138.3 -87340.4 25.0 7 "Ayd\\U+0131nlatma linyesi, ok: panoya d\\U+00F6n\\U+00FC\\U+015F, etiket PANO/L\\U+0130NYE")
   ("I" "CLD-P2-ICT-TABLO" "CLD_S_PRIZ" 146988.3 -87420.4 0.0 2.167)
   ("T" "CLD-P2-ICT-TABLO" 147138.3 -87420.4 25.0 7 "Toprakl\\U+0131 priz 16 A (h=40 cm, tezgah h=110 cm)")
   ("I" "CLD-P2-ICT-TABLO" "CLD_S_PRIZU" 146988.3 -87500.4 0.0 2.167)
   ("T" "CLD-P2-ICT-TABLO" 147138.3 -87500.4 25.0 7 "Bilgisayar prizi (ayr\\U+0131 linye, UPS haz\\U+0131rl\\U+0131\\U+011F\\U+0131)")
   ("I" "CLD-P2-ICT-TABLO" "CLD_S_PRIZE" 146988.3 -87580.4 0.0 2.167)
   ("T" "CLD-P2-ICT-TABLO" 147138.3 -87580.4 25.0 7 "Etanj priz IP44")
   ("I" "CLD-P2-ICT-TABLO" "CLD_S_PGRUP" 146988.3 -87660.4 0.0 1.3)
   ("T" "CLD-P2-ICT-TABLO" 147138.3 -87660.4 25.0 7 "End\\U+00FCstriyel priz grubu CEE 32A+16A+2x16A (i\\U+00E7 koruma, h=150 cm)")
   ("I" "CLD-P2-ICT-TABLO" "CLD_S_CK_ISITICI" 146988.3 -87740.4 0.0 2.167)
   ("T" "CLD-P2-ICT-TABLO" 147138.3 -87740.4 25.0 7 "Ani su \\U+0131s\\U+0131t\\U+0131c\\U+0131 \\U+00E7\\U+0131k\\U+0131\\U+015F\\U+0131 (IS) - ayr\\U+0131 linye")
   ("I" "CLD-P2-ICT-TABLO" "CLD_S_CK_TERMOSIFON" 146988.3 -87820.4 0.0 2.167)
   ("T" "CLD-P2-ICT-TABLO" 147138.3 -87820.4 25.0 7 "Elektrikli termosifon \\U+00E7\\U+0131k\\U+0131\\U+015F\\U+0131 (TS) - ayr\\U+0131 linye")
   ("I" "CLD-P2-ICT-TABLO" "CLD_S_CK_BULASIK" 146988.3 -87900.4 0.0 2.167)
   ("T" "CLD-P2-ICT-TABLO" 147138.3 -87900.4 25.0 7 "Bula\\U+015F\\U+0131k makinesi \\U+00E7\\U+0131k\\U+0131\\U+015F\\U+0131 (B) - ayr\\U+0131 linye")
   ("I" "CLD-P2-ICT-TABLO" "CLD_S_CK_ASPIRATOR" 146988.3 -87980.4 0.0 2.167)
   ("T" "CLD-P2-ICT-TABLO" 147138.3 -87980.4 25.0 7 "Havaland\\U+0131rma cihaz\\U+0131 / aspirat\\U+00F6r \\U+00E7\\U+0131k\\U+0131\\U+015F\\U+0131 (A) - ayr\\U+0131 linye")
   ("P" "CLD-P2-ICT-LINYE-PRIZ" nil 0.0 ((146863.3 -88060.4) (147113.3 -88060.4)))
   ("T" "CLD-P2-ICT-TABLO" 147138.3 -88060.4 25.0 7 "Priz / kuvvet linyesi, ok: panoya d\\U+00F6n\\U+00FC\\U+015F")))))
(defun cld:ops-p2_elektrik_ic_tesisat-6 () (cld:play (quote (
   ("TB" "CLD-P2-ICT-TABLO" 148570.8 -86302.9 25.0 "L\\U+0130NYE L\\U+0130STES\\U+0130 (1)" (("PANO" "L\\U+0130NYE" "T\\U+00DCR" "A\\U+00C7IKLAMA" "ADET" "G\\U+00DC\\U+00C7 (W)" "FAZ" "S\\U+0130GORTA" "KA\\U+00C7AK AKIM" "KABLO" "L (m)" "%e") ("IDP-ZK" "A1" "Ayd\\U+0131nlatma" "Ayd\\U+0131nlatma" "7" "186" "T" "B10A" "30 mA" "NYM 3x1,5 mm\\U+00B2" "23,6" "0,20") ("IDP-ZK" "AC2" "Acil ayd." "Acil ayd\\U+0131nlatma / y\\U+00F6nlendirme" "6" "18" "T" "B10A" "30 mA" "NYM 3x1,5 mm\\U+00B2" "15,6" "0,01") ("IDP-ZK" "P3" "Priz" "Priz" "5" "1.500" "S" "B16A" "30 mA" "NYM 3x2,5 mm\\U+00B2" "13,2" "0,53") ("IDP-ZK" "K4" "Kuvvet" "S\\U+0131\\U+011F\\U+0131nak havaland\\U+0131rma cihaz\\U+0131" "1" "750" "T" "B10A" "30 mA" "NYM 3x1,5 mm\\U+00B2" "5,3" "0,18") ("IDP-ZK" "K5" "Kuvvet" "Elektrikli termosifon 80 L 2 kW" "1" "2.000" "R" "B16A" "30 mA" "NYM 3x2,5 mm\\U+00B2" "7,6" "0,41") ("UTP-2" "A1" "Ayd\\U+0131nlatma" "Ayd\\U+0131nlatma (y\\U+00FCksek tavan, AK: s\\U+00FCrekli faz)" "3" "450" "S" "B10A" "30 mA" "NYM 4x1,5 mm\\U+00B2" "36,8" "0,74") ("UTP-2" "A2" "Ayd\\U+0131nlatma" "Ayd\\U+0131nlatma (y\\U+00FCksek tavan, AK: s\\U+00FCrekli faz)" "8" "1.200" "R" "B16A" "30 mA" "NYM 4x4 mm\\U+00B2" "60,5" "1,23") ("UTP-2" "A3" "Ayd\\U+0131nlatma" "Ayd\\U+0131nlatma (y\\U+00FCksek tavan, AK: s\\U+00FCrekli faz)" "8" "1.200" "S" "B16A" "30 mA" "NYM 4x4 mm\\U+00B2" "70,1" "1,42") ("UTP-2" "A4" "Ayd\\U+0131nlatma" "Ayd\\U+0131nlatma (y\\U+00FCksek tavan, AK: s\\U+00FCrekli faz)" "8" "1.200" "T" "B16A" "30 mA" "NYM 4x4 mm\\U+00B2" "57,9" "1,17") ("UTP-2" "A5" "Ayd\\U+0131nlatma" "Ayd\\U+0131nlatma (y\\U+00FCksek tavan, AK: s\\U+00FCrekli faz)" "8" "1.200" "R" "B16A" "30 mA" "NYM 4x2,5 mm\\U+00B2" "45,1" "1,46") ("UTP-2" "A6" "Ayd\\U+0131nlatma" "Ayd\\U+0131nlatma (y\\U+00FCksek tavan)" "1" "150" "T" "B10A" "30 mA" "NYM 3x1,5 mm\\U+00B2" "37,4" "0,25") ("UTP-2" "AC7" "Acil ayd." "Acil ayd\\U+0131nlatma / y\\U+00F6nlendirme" "2" "6" "T" "B10A" "30 mA" "NYM 3x1,5 mm\\U+00B2" "31,0" "0,01") ("UTP-2" "AC8" "Acil ayd." "Acil ayd\\U+0131nlatma / y\\U+00F6nlendirme" "1" "3" "T" "B10A" "30 mA" "NYM 3x1,5 mm\\U+00B2" "36,9" "0,00") ("UTP-2" "G9" "End. priz" "End. priz grubu (4P C32+C16+2xB16)" "1" "5.000" "RST" "C32A" "30 mA A tipi (kutu i\\U+00E7i)" "NYM 5x10 mm\\U+00B2" "28,5" "0,35") ("UTP-2" "G10" "End. priz" "End. priz grubu (4P C32+C16+2xB16)" "1" "5.000" "RST" "C32A" "30 mA A tipi (kutu i\\U+00E7i)" "NYM 5x10 mm\\U+00B2" "36,8" "0,45") ("UTP-2" "G11" "End. priz" "End. priz grubu (4P C32+C16+2xB16)" "1" "5.000" "RST" "C32A" "30 mA A tipi (kutu i\\U+00E7i)" "NYM 5x10 mm\\U+00B2" "30,7" "0,38") ("UTP-2" "G12" "End. priz" "End. priz grubu (4P C32+C16+2xB16)" "1" "5.000" "RST" "C32A" "30 mA A tipi (kutu i\\U+00E7i)" "NYM 5x10 mm\\U+00B2" "6,4" "0,08") ("UTP-2" "G13" "End. priz" "End. priz grubu (4P C32+C16+2xB16)" "1" "5.000" "RST" "C32A" "30 mA A tipi (kutu i\\U+00E7i)" "NYM 5x10 mm\\U+00B2" "29,6" "0,36") ("UTP-2" "G14" "End. priz" "End. priz grubu (4P C32+C16+2xB16)" "1" "5.000" "RST" "C32A" "30 mA A tipi (kutu i\\U+00E7i)" "NYM 5x10 mm\\U+00B2" "34,0" "0,42") ("UTP-2" "G15" "End. priz" "End. priz grubu (4P C32+C16+2xB16)" "1" "5.000" "RST" "C32A" "30 mA A tipi (kutu i\\U+00E7i)" "NYM 5x10 mm\\U+00B2" "26,3" "0,32") ("UTP-2" "K16" "Kuvvet" "Ayd\\U+0131nlatma kumanda (kontakt\\U+00F6r/saat r\\U+00F6lesi)" "1" "50" "T" "B10A" "30 mA" "NYM 3x1,5 mm\\U+00B2" "3,0" "0,01") ("UTP-2" "K17" "Kuvvet" "Seksiyonel kap\\U+0131 motoru (L\\U+224825 m kabul)" "1" "750" "RST" "C10A" "300 mA" "NYM 5x1,5 mm\\U+00B2" "25,0" "0,14") ("UTP-1" "A1" "Ayd\\U+0131nlatma" "Ayd\\U+0131nlatma (y\\U+00FCksek tavan, AK: s\\U+00FCrekli faz)" "8" "1.200" "R" "B16A" "30 mA" "NYM 4x4 mm\\U+00B2" "53,7" "1,09") ("UTP-1" "A2" "Ayd\\U+0131nlatma" "Ayd\\U+0131nlatma (y\\U+00FCksek tavan, AK: s\\U+00FCrekli faz)" "8" "1.200" "S" "B16A" "30 mA" "NYM 4x4 mm\\U+00B2" "62,4" "1,26") ("UTP-1" "A3" "Ayd\\U+0131nlatma" "Ayd\\U+0131nlatma (y\\U+00FCksek tavan, AK: s\\U+00FCrekli faz)" "8" "1.200" "T" "B16A" "30 mA" "NYM 4x4 mm\\U+00B2" "69,7" "1,41") ("UTP-1" "A4" "Ayd\\U+0131nlatma" "Ayd\\U+0131nlatma (y\\U+00FCksek tavan, AK: s\\U+00FCrekli faz)" "8" "1.200" "R" "B16A" "30 mA" "NYM 4x4 mm\\U+00B2" "70,1" "1,42") ("UTP-1" "A5" "Ayd\\U+0131nlatma" "Ayd\\U+0131nlatma (y\\U+00FCksek tavan, AK: s\\U+00FCrekli faz)" "3" "450" "S" "B10A" "30 mA" "NYM 4x1,5 mm\\U+00B2" "37,8" "0,77") ("UTP-1" "AC6" "Acil ayd." "Acil ayd\\U+0131nlatma / y\\U+00F6nlendirme" "2" "6" "T" "B10A" "30 mA" "NYM 3x1,5 mm\\U+00B2" "39,2" "0,01") ("UTP-1" "AC7" "Acil ayd." "Acil ayd\\U+0131nlatma / y\\U+00F6nlendirme" "2" "6" "T" "B10A" "30 mA" "NYM 3x1,5 mm\\U+00B2" "45,0" "0,01") ("UTP-1" "AC8" "Acil ayd." "Acil ayd\\U+0131nlatma / y\\U+00F6nlendirme" "1" "3" "T" "B10A" "30 mA" "NYM 3x1,5 mm\\U+00B2" "22,3" "0,00") ("UTP-1" "G9" "End. priz" "End. priz grubu (4P C32+C16+2xB16)" "1" "5.000" "RST" "C32A" "30 mA A tipi (kutu i\\U+00E7i)" "NYM 5x10 mm\\U+00B2" "33,2" "0,41") ("UTP-1" "G10" "End. priz" "End. priz grubu (4P C32+C16+2xB16)" "1" "5.000" "RST" "C32A" "30 mA A tipi (kutu i\\U+00E7i)" "NYM 5x10 mm\\U+00B2" "7,9" "0,10") ("UTP-1" "G11" "End. priz" "End. priz grubu (4P C32+C16+2xB16)" "1" "5.000" "RST" "C32A" "30 mA A tipi (kutu i\\U+00E7i)" "NYM 5x10 mm\\U+00B2" "26,7" "0,33") ("UTP-1" "G12" "End. priz" "End. priz grubu (4P C32+C16+2xB16)" "1" "5.000" "RST" "C32A" "30 mA A tipi (kutu i\\U+00E7i)" "NYM 5x10 mm\\U+00B2" "31,6" "0,39") ("UTP-1" "G13" "End. priz" "End. priz grubu (4P C32+C16+2xB16)" "1" "5.000" "RST" "C32A" "30 mA A tipi (kutu i\\U+00E7i)" "NYM 5x10 mm\\U+00B2" "33,1" "0,41") ("UTP-1" "G14" "End. priz" "End. priz grubu (4P C32+C16+2xB16)" "1" "5.000" "RST" "C32A" "30 mA A tipi (kutu i\\U+00E7i)" "NYM 5x10 mm\\U+00B2" "25,3" "0,31") ("UTP-1" "G15" "End. priz" "End. priz grubu (4P C32+C16+2xB16)" "1" "5.000" "RST" "C32A" "30 mA A tipi (kutu i\\U+00E7i)" "NYM 5x10 mm\\U+00B2" "34,8" "0,43") ("UTP-1" "K16" "Kuvvet" "Ayd\\U+0131nlatma kumanda (kontakt\\U+00F6r/saat r\\U+00F6lesi)" "1" "50" "T" "B10A" "30 mA" "NYM 3x1,5 mm\\U+00B2" "3,0" "0,01") ("UTP-1" "K17" "Kuvvet" "Seksiyonel kap\\U+0131 motoru (L\\U+224825 m kabul)" "1" "750" "RST" "C10A" "300 mA" "NYM 5x1,5 mm\\U+00B2" "25,0" "0,14") ("IDP-1K" "A1" "Ayd\\U+0131nlatma" "Ayd\\U+0131nlatma" "10" "162" "T" "B10A" "30 mA" "NYM 3x1,5 mm\\U+00B2" "21,6" "0,16") ("IDP-1K" "A2" "Ayd\\U+0131nlatma" "Ayd\\U+0131nlatma" "3" "54" "T" "B10A" "30 mA" "NYM 3x1,5 mm\\U+00B2" "10,5" "0,03") ("IDP-1K" "AC3" "Acil ayd." "Acil ayd\\U+0131nlatma / y\\U+00F6nlendirme" "2" "6" "T" "B10A" "30 mA" "NYM 3x1,5 mm\\U+00B2" "9,3" "0,00") ("IDP-1K" "P4" "Priz" "Priz" "6" "1.800" "T" "B16A" "30 mA" "NYM 3x2,5 mm\\U+00B2" "20,6" "1,00") ("IDP-1K" "K5" "Kuvvet" "Ani su \\U+0131s\\U+0131t\\U+0131c\\U+0131 3,5 kW" "1" "3.500" "R" "B25A" "30 mA" "NYM 3x4 mm\\U+00B2" "5,8" "0,34") ("IDP-1K" "K6" "Kuvvet" "Ani su \\U+0131s\\U+0131t\\U+0131c\\U+0131 3,5 kW" "1" "3.500" "S" "B25A" "30 mA" "NYM 3x4 mm\\U+00B2" "3,5" "0,21")))
   ("TB" "CLD-P2-ICT-TABLO" 148570.8 -88977.9 25.0 "L\\U+0130NYE L\\U+0130STES\\U+0130 (2)" (("PANO" "L\\U+0130NYE" "T\\U+00DCR" "A\\U+00C7IKLAMA" "ADET" "G\\U+00DC\\U+00C7 (W)" "FAZ" "S\\U+0130GORTA" "KA\\U+00C7AK AKIM" "KABLO" "L (m)" "%e") ("IDP-1K" "K7" "Kuvvet" "VRF i\\U+00E7 \\U+00FCniteleri besleme" "2" "220" "T" "B10A" "30 mA A tipi" "NYM 3x1,5 mm\\U+00B2" "9,6" "0,09")))
   ("NT" "CLD-P2-ICT-TABLO" 148570.8 -89452.9 25.0 "NOTLAR" ("1- Tesisat Elektrik \\U+0130\\U+00E7 Tesisleri Y\\U+00F6netmeli\\U+011Fi, TS HD 60364 ve TS EN 12464-1 esas al\\U+0131narak hesaplanm\\U+0131\\U+015Ft\\U+0131r." "2- Ayd\\U+0131nlatma ve priz tesisat\\U+0131 ayr\\U+0131 paftalarda g\\U+00F6sterilmi\\U+015Ftir; linye etiketi \"PANO/L\\U+0130NYE\", ok y\\U+00F6n\\U+00FC panoyu g\\U+00F6sterir." "3- Kesitler IEC 60364-5-52 C y\\U+00F6ntemi x 0,80 (ofis) / x 0,71 (\\U+00FCretim hol\\U+00FC tavas\\U+0131, 40 \\U+00B0C) ile se\\U+00E7ilmi\\U+015Ftir; gerilim d\\U+00FC\\U+015F\\U+00FCm\\U+00FC ayd\\U+0131nlatma ve prizde \\U+2264 %1,5, kuvvette \\U+2264 %3 olacak \\U+015Fekilde linyeler b\\U+00F6l\\U+00FCnm\\U+00FC\\U+015Ft\\U+00FCr." "4- Ka\\U+00E7ak ak\\U+0131m: t\\U+00FCm tek fazl\\U+0131 son devreler (priz, ayd\\U+0131nlatma, \\U+0131slak hacim, \\U+00F6zel \\U+00E7\\U+0131k\\U+0131\\U+015F) 30 mA, bilgisayar/VRF A tipi; 3 fazl\\U+0131 motor devreleri 300 mA; pano giri\\U+015Fleri 300 mA S (se\\U+00E7ici) - TS HD 60364-4-41 411.3.3, EMO." "5- Ofis ve \\U+0131slak hacimlerde s\\U+0131va alt\\U+0131 spiral boru, \\U+00FCretim alan\\U+0131nda galvaniz kablo tavas\\U+0131 / boru kullan\\U+0131lacakt\\U+0131r." "6- \"AK\" acil kitli armat\\U+00FCrler kontakt\\U+00F6r \\U+00F6ncesinden s\\U+00FCrekli faz ile beslenir (NYM 4x..: L anahtarl\\U+0131 + L s\\U+00FCrekli, TS EN 50172)." "7- Acil ve y\\U+00F6nlendirme armat\\U+00FCrleri 3 saat bataryal\\U+0131d\\U+0131r (Binalar\\U+0131n Yang\\U+0131ndan Korunmas\\U+0131 Hakk\\U+0131nda Y\\U+00F6netmelik, TS EN 1838)." "8- End\\U+00FCstriyel priz grubu kutusu i\\U+00E7inde 4P C32, C16 ve 2xB16 sigortalar ile 30 mA (A tipi) ka\\U+00E7ak ak\\U+0131m r\\U+00F6lesi bulunur." "9- Anahtarlar sahada kap\\U+0131 a\\U+00E7\\U+0131l\\U+0131\\U+015F y\\U+00F6n\\U+00FCne g\\U+00F6re kap\\U+0131 kanad\\U+0131n\\U+0131n arkas\\U+0131nda kalmayacak \\U+015Fekilde yerle\\U+015Ftirilecektir." "10- \\U+00DCretim alan\\U+0131 ayd\\U+0131nlatmas\\U+0131 tali panodan kontakt\\U+00F6r + saat r\\U+00F6lesi ile kumanda edilir."))
   ("P" "CLD-P2-ICT-PAFTA" T 10.0 ((146638.3 -91257.9) (152372.3 -91257.9) (152372.3 -86002.9) (146638.3 -86002.9)))
   ("P" "CLD-P2-ICT-PAFTA" nil 6.0 ((146638.3 -90507.9) (152372.3 -90507.9)))
   ("T" "CLD-P2-ICT-YAZI" 146738.3 -90697.9 70.0 0 "HESAP TABLOLARI, CETVELLER VE NOTLAR")
   ("T" "CLD-P2-ICT-YAZI" 146738.3 -90857.9 40.0 0 "ELEKTR\\U+0130K \\U+0130\\U+00C7 TES\\U+0130SAT PROJES\\U+0130  -  \\U+00D6l\\U+00E7eksiz")
   ("P" "CLD-P2-ICT-PAFTA" T 6.0 ((149872.3 -91237.9) (152372.3 -91237.9) (152372.3 -90527.9) (149872.3 -90527.9)))
   ("T" "CLD-P2-ICT-YAZI" 149902.3 -90593.8 18.0 0 "\\U+0130\\U+015E\\U+0130N ADI")
   ("T" "CLD-P2-ICT-YAZI" 150492.3 -90593.8 20.0 0 "ELEKTR\\U+0130K \\U+0130\\U+00C7 TES\\U+0130SAT PROJES\\U+0130")
   ("L" "CLD-P2-ICT-PAFTA" 149872.3 -90629.3 152372.3 -90629.3)
   ("T" "CLD-P2-ICT-YAZI" 149902.3 -90695.2 18.0 0 "YAPI SAH\\U+0130B\\U+0130")
   ("T" "CLD-P2-ICT-YAZI" 150492.3 -90695.2 20.0 0 "BROSCO \\U+0130THALAT \\U+0130HRACAT VE T\\U+0130CARET ANON\\U+0130M \\U+015E\\U+0130RKET\\U+0130")
   ("L" "CLD-P2-ICT-PAFTA" 149872.3 -90730.7 152372.3 -90730.7)
   ("T" "CLD-P2-ICT-YAZI" 149902.3 -90796.7 18.0 0 "ADRES")
   ("T" "CLD-P2-ICT-YAZI" 150492.3 -90796.7 20.0 0 "YUKARI MAHALLE / KEMALPA\\U+015EA / \\U+0130ZM\\U+0130R  -  Ada: ......  Parsel: 2")
   ("L" "CLD-P2-ICT-PAFTA" 149872.3 -90832.2 152372.3 -90832.2)
   ("T" "CLD-P2-ICT-YAZI" 149902.3 -90898.1 18.0 0 "PAFTA ADI")
   ("T" "CLD-P2-ICT-YAZI" 150492.3 -90898.1 20.0 0 "HESAP TABLOLARI VE NOTLAR")
   ("L" "CLD-P2-ICT-PAFTA" 149872.3 -90933.6 152372.3 -90933.6)
   ("T" "CLD-P2-ICT-YAZI" 149902.3 -90999.5 18.0 0 "\\U+00D6L\\U+00C7EK / TAR\\U+0130H / PAFTA NO")
   ("T" "CLD-P2-ICT-YAZI" 150492.3 -90999.5 20.0 0 "\\U+00D6l\\U+00E7eksiz   |   19.10.2026   |   01-05")
   ("L" "CLD-P2-ICT-PAFTA" 149872.3 -91035.0 152372.3 -91035.0)
   ("T" "CLD-P2-ICT-YAZI" 149902.3 -91100.9 18.0 0 "PROJE M\\U+00DCELL\\U+0130F\\U+0130")
   ("T" "CLD-P2-ICT-YAZI" 150492.3 -91100.9 20.0 0 "Elektrik M\\U+00FChendisi - Ad\\U+0131 Soyad\\U+0131: ..............................")
   ("L" "CLD-P2-ICT-PAFTA" 149872.3 -91136.4 152372.3 -91136.4)
   ("T" "CLD-P2-ICT-YAZI" 149902.3 -91202.4 18.0 0 "ODA S\\U+0130C\\U+0130L / SMM NO")
   ("T" "CLD-P2-ICT-YAZI" 150492.3 -91202.4 20.0 0 "EMO Sicil No: ............   SMM Belge No: ............   \\U+0130mza: ............")
   ("L" "CLD-P2-ICT-PAFTA" 150462.3 -91237.9 150462.3 -90527.9)))))

(defun c:CLD_P2_ICTESISAT ( / *error* olderr)
  (setq *error* cld:err)
  (setq *cld-u* 100.0 *cld-ext* (list 0.0 0.0 1.0))
  (cld:begin "CLD-P2-ICT-*")
  (cld:unlock "CLD-P2-ICT-*")
  (cld:unlock "CLD-ICT-*")
  (cld:clear "CLD-ICT-*")
  (cld:ops-p2_elektrik_ic_tesisat-layers)
  (cld:clear "CLD-P2-ICT-*")
  (cld:def-symbols)
  (cld:ops-p2_elektrik_ic_tesisat-1)
  (cld:ops-p2_elektrik_ic_tesisat-2)
  (cld:ops-p2_elektrik_ic_tesisat-3)
  (cld:ops-p2_elektrik_ic_tesisat-4)
  (cld:ops-p2_elektrik_ic_tesisat-5)
  (cld:ops-p2_elektrik_ic_tesisat-6)
  (cld:end "CLD: Parsel 2 - ELEKTRIK IC TESISAT PROJESI cizildi")
  (princ))

(if (cld:wrong-dwg "2" (list "3" "4" "5"))
  (princ "\nCLD UYARI: Bu dosya PARSEL 2 icindir; acik cizim baska bir parsele ait gorunuyor. Yine de cizmek icin CLD_P2_ICTESISAT yazin.")
  (progn (princ "\nCLD: Parsel 2 ELEKTRIK_IC_TESISAT yukleniyor, cizim olusturuluyor...") (c:CLD_P2_ICTESISAT)))
(princ "\nCLD: Yeniden cizmek icin komut: CLD_P2_ICTESISAT")
(princ)
