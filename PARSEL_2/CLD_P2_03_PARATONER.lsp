;;; ==========================================================================
;;; CLD_P2_03_PARATONER.lsp
;;; PARSEL 2 - PARATONER (YILDIRIMDAN KORUNMA) PROJESI
;;; Isveren : BROSCO ITHALAT IHRACAT VE TICARET ANONIM SIRKETI
;;; Konum   : YUKARI MAHALLE / KEMALPASA / IZMIR
;;; Kaynak  : BROSCO 2 NOLU PARSEL MIMARI.dwg (mimari paftalar)
;;; Kullanim: APPLOAD ile yukleyin -> cizim otomatik olusur.
;;;          Yeniden cizmek icin komut: CLD_P2_PARATONER
;;;          Tum ciktilar "CLD-P2-PAR-*" katmanlarindadir; yeniden calistirmada bu katmanlar temizlenir.
;;;          Guvenlik uyarisi gelirse "Bir kez yukle" deyin veya klasoru Secenekler > Dosyalar >
;;;          Guvenilen Konumlar (TRUSTEDPATHS) listesine ekleyin.
;;; Uretici : CLD (Claude) otomatik muhendislik motoru - tum isimler CLD onekli.
;;;   Mimari: 2 kat, 12 mahal, kat kotlari ZK=+0.00, 1K=+3.00, bina yuksekligi 11.21 m
;;;   Elektrik: kurulu 238.6 kW, talep 148.5 kW, trafo 250 kVA, KMP 90 kVAr, jenerator 45 kVA
;;;   Aydinlatma: 107 armatur, 29 priz/cikis, 46 linye, 8 pano
;;;   Topraklama: R=0.97 ohm (birlesik), paratoner LPL I, 27 inis
;;;   Mekanik: VRF 4.4 kW ic unite, dis unite 5.0 kW
;;;   Sihhi: 12 armatur, 1 pis su kolonu, 14 yagmur inisi
;;; ==========================================================================

;;; ==========================================================================
;;; CLD CORE  -  ortak cizim altyapisi (katman, stil, varlik, tablo, oynatici)
;;; Tum isimler CLD onekli. ActiveX (vla-) kullanilmaz: AutoCAD / BricsCAD /
;;; accoreconsole uyumlu saf AutoLISP + entmake.
;;; Mimari paftalar WCS XZ duzleminde (ekstruzyon 0,-1,0) cizildiginden tum
;;; varliklar ayni duzlemde (*cld-ext*) uretilir; koordinatlar pafta (OCS)
;;; koordinatidir.
;;; ==========================================================================

(setq *cld-ver* "1.0")
(if (not *cld-ext*) (setq *cld-ext* '(0.0 0.0 1.0)))
(if (not *cld-u*) (setq *cld-u* 100.0))

;;; ---------------------------------------------------------------- yardimci
(defun cld:m (x) (* x *cld-u*))
(defun cld:3d (p) (list (float (car p)) (float (cadr p)) 0.0))
(defun cld:2d (p) (list (float (car p)) (float (cadr p))))
(defun cld:pxy (p dx dy) (list (+ (car p) dx) (+ (cadr p) dy)))
(defun cld:wcs (p) (trans (cld:3d p) *cld-ext* 0))
(defun cld:top (lay) (/= lay "0"))
(defun cld:x210 (lay) (if (cld:top lay) (list (cons 210 *cld-ext*) '(410 . "Model")) '()))
;; renk / cizgi tipi / kalinlik her zaman acik yazilir: cizimdeki CECOLOR / CELTYPE / CELWEIGHT ne olursa olsun
;; katmandan (ByLayer) gelir; blok icindekiler ByBlock
(defun cld:col (lay)
  (if (= lay "0") '((62 . 0) (6 . "ByBlock") (370 . -2)) '((62 . 256) (6 . "ByLayer") (370 . -1))))
(defun cld:dlen (s / n i)
  ;; gorunen karakter sayisi (\U+XXXX = 1 karakter)
  (setq n 0 i 1)
  (while (<= i (strlen s))
    (if (and (= (substr s i 3) "\\U+") (<= (+ i 6) (strlen s))) (setq i (+ i 7)) (setq i (1+ i)))
    (setq n (1+ n)))
  n)
(defun cld:maxl (l) (if l (apply 'max l) 0))
(defun cld:sum (l) (apply '+ (cons 0 l)))
(defun cld:nth-or (i l def) (if (and l (< i (length l))) (nth i l) def))
(defun cld:range (n / i r) (setq i (1- n)) (while (>= i 0) (setq r (cons i r) i (1- i))) r)

;;; ------------------------------------------------------ tablo kayitlari
(defun cld:ltype (nm desc dash gap / sc)
  (if (not (tblsearch "LTYPE" nm))
    (progn
      (setq sc (max 1e-6 (getvar "LTSCALE")))
      (entmake (list '(0 . "LTYPE") '(100 . "AcDbSymbolTableRecord") '(100 . "AcDbLinetypeTableRecord")
                     (cons 2 nm) '(70 . 0) (cons 3 desc) '(72 . 65) '(73 . 2)
                     (cons 40 (/ (+ dash gap) sc)) (cons 49 (/ dash sc)) '(74 . 0) (cons 49 (- (/ gap sc))) '(74 . 0)))))
  nm)
(defun cld:style ()
  (if (not (tblsearch "STYLE" "CLD_YAZI"))
    (entmake '((0 . "STYLE") (100 . "AcDbSymbolTableRecord") (100 . "AcDbTextStyleTableRecord")
               (2 . "CLD_YAZI") (70 . 0) (40 . 0.0) (41 . 0.85) (50 . 0.0) (71 . 0) (42 . 2.5)
               (3 . "arial.ttf") (4 . ""))))
  "CLD_YAZI")
(defun cld:lay (nm col lt lw / e ed)
  (if (not (tblsearch "LAYER" nm))
    (entmake (list '(0 . "LAYER") '(100 . "AcDbSymbolTableRecord") '(100 . "AcDbLayerTableRecord")
                   (cons 2 nm) '(70 . 0) (cons 62 col)
                   (cons 6 (if (and lt (tblsearch "LTYPE" lt)) lt "Continuous"))
                   (cons 370 lw)))
    (progn
      (setq e (tblobjname "LAYER" nm) ed (entget e))
      (setq ed (subst (cons 70 0) (assoc 70 ed) ed))
      (setq ed (subst (cons 62 col) (assoc 62 ed) ed))
      (if (and lt (tblsearch "LTYPE" lt) (assoc 6 ed)) (setq ed (subst (cons 6 lt) (assoc 6 ed) ed)))
      (if (assoc 370 ed) (setq ed (subst (cons 370 lw) (assoc 370 ed) ed)))
      (entmod ed)))
  nm)

;;; ---------------------------------------------------- varlik olusturucular
;;; lay "0" = blok tanimi icerigi (BYBLOCK renk, blok koordinati)
(defun cld:e-line (a b lay)
  (append (list '(0 . "LINE") (cons 8 lay)) (cld:col lay)
          (if (cld:top lay) (list (cons 10 (cld:wcs a)) (cons 11 (cld:wcs b))) (list (cons 10 (cld:3d a)) (cons 11 (cld:3d b))))
          (cld:x210 lay)))
(defun cld:e-circle (c r lay)
  (append (list '(0 . "CIRCLE") (cons 8 lay)) (cld:col lay) (list (cons 10 (cld:3d c)) (cons 40 r)) (cld:x210 lay)))
(defun cld:e-arc (c r a1 a2 lay)
  (append (list '(0 . "ARC") (cons 8 lay)) (cld:col lay) (list (cons 10 (cld:3d c)) (cons 40 r) (cons 50 a1) (cons 51 a2)) (cld:x210 lay)))
(defun cld:e-pl (pts closed w lay)
  (append (list '(0 . "LWPOLYLINE") '(100 . "AcDbEntity") (cons 8 lay)) (cld:col lay)
          (list '(100 . "AcDbPolyline") (cons 90 (length pts)) (cons 70 (+ (if closed 1 0) (if (cld:top lay) 128 0))) (cons 43 w) '(38 . 0.0))
          (mapcar '(lambda (p) (cons 10 (cld:2d p))) pts)
          (cld:x210 lay)))
(defun cld:e-dot (c r lay)
  (append (list '(0 . "LWPOLYLINE") '(100 . "AcDbEntity") (cons 8 lay)) (cld:col lay)
          (list '(100 . "AcDbPolyline") '(90 . 2) '(70 . 1) (cons 43 r) '(38 . 0.0)
                (cons 10 (list (- (car c) (/ r 2.0)) (cadr c))) '(42 . 1.0)
                (cons 10 (list (+ (car c) (/ r 2.0)) (cadr c))) '(42 . 1.0))
          (cld:x210 lay)))
(defun cld:e-solid (p1 p2 p3 p4 lay)
  (append (list '(0 . "SOLID") (cons 8 lay)) (cld:col lay)
          (list (cons 10 (cld:3d p1)) (cons 11 (cld:3d p2)) (cons 12 (cld:3d p4)) (cons 13 (cld:3d p3)))
          (cld:x210 lay)))
(defun cld:e-text (p h s j lay / ed p3)
  ;; j: 0 sol-taban, 1 orta-taban, 2 sag-taban, 4 orta-orta, 7 sol-orta, 9 sag-orta
  (setq p3 (cld:3d p))
  (setq ed (append (list '(0 . "TEXT") (cons 8 lay)) (cld:col lay)
                   (list (cons 7 (cld:style)) (cons 10 p3) (cons 40 h) (cons 1 s) '(50 . 0.0) '(41 . 0.85))))
  (setq ed (cond ((= j 1) (append ed (list '(72 . 1) (cons 11 p3) '(73 . 0))))
                 ((= j 2) (append ed (list '(72 . 2) (cons 11 p3) '(73 . 0))))
                 ((= j 4) (append ed (list '(72 . 1) (cons 11 p3) '(73 . 2))))
                 ((= j 7) (append ed (list '(72 . 0) (cons 11 p3) '(73 . 2))))
                 ((= j 9) (append ed (list '(72 . 2) (cons 11 p3) '(73 . 2))))
                 (T ed)))
  (append ed (cld:x210 lay)))
(defun cld:e-ins (blk p sc rot lay)
  (append (list '(0 . "INSERT") (cons 8 lay)) (cld:col lay) (list (cons 2 blk) (cons 10 (cld:3d p))
                (cons 41 sc) (cons 42 sc) (cons 43 sc) (cons 50 rot))
          (cld:x210 lay)))
(defun cld:line (a b lay) (entmake (cld:e-line a b lay)))
(defun cld:pl (pts closed w lay) (if (cdr pts) (entmake (cld:e-pl pts closed w lay))))
(defun cld:txt (p h s j lay) (entmake (cld:e-text p h s j lay)))
(defun cld:rect (p1 p2 lay) (cld:pl (list p1 (list (car p2) (cadr p1)) p2 (list (car p1) (cadr p2))) T 0.0 lay))

;;; ------------------------------------------------------------ blok tanimi
(defun cld:defblk (name ents)
  (if (not (tblsearch "BLOCK" name))
    (progn
      (entmake (list '(0 . "BLOCK") (cons 2 name) '(70 . 0) '(10 0.0 0.0 0.0) '(8 . "0")))
      (foreach e ents (entmake e))
      (entmake '((0 . "ENDBLK") (8 . "0")))))
  name)

;;; mimari altlik blogu: plines ((kapali (x y) (x y) ...) ...)  texts ((x y h "yazi") ...)
(defun cld:defblk-bg (name plines texts)
  (if (not (tblsearch "BLOCK" name))
    (progn
      (entmake (list '(0 . "BLOCK") (cons 2 name) '(70 . 0) '(10 0.0 0.0 0.0) '(8 . "0")))
      (foreach p plines (if (cddr p) (entmake (cld:e-pl (cdr p) (car p) 0.0 "0"))))
      (foreach s texts (entmake (cld:e-text (list (car s) (cadr s)) (caddr s) (cadddr s) 4 "0")))
      (entmake '((0 . "ENDBLK") (8 . "0")))))
  name)

;;; ------------------------------------------------------------------ tablo
;;; rows: ((hucre ...) ...)  ilk satir baslik. Sutun genislikleri otomatik.
(defun cld:table (org title rows h lay / ncol widths rh y x w i r cw tw pad s)
  (setq pad (* 0.6 h) rh (* 2.0 h))
  (setq ncol (cld:maxl (mapcar 'length rows)))
  (setq widths (mapcar '(lambda (c)
                          (+ (* 2 pad) (* 0.66 h (cld:maxl (mapcar '(lambda (r) (cld:dlen (cld:nth-or c r ""))) rows)))))
                       (cld:range ncol)))
  (setq tw (cld:sum widths) x (car org) y (cadr org))
  (if (and title (/= title ""))
    (progn
      (cld:rect (list x y) (list (+ x tw) (- y (* 1.5 rh))) lay)
      (cld:txt (list (+ x pad) (- y (* 0.75 rh))) (* 1.3 h) title 7 lay)
      (setq y (- y (* 1.5 rh)))))
  (setq i 0)
  (foreach r rows
    (setq x (car org) cw 0)
    (cld:rect (list x y) (list (+ x tw) (- y rh)) lay)
    (foreach w widths
      (if (> cw 0) (cld:line (list x y) (list x (- y rh)) lay))
      (setq s (cld:nth-or cw r ""))
      (if (/= s "") (cld:txt (list (+ x pad) (- y (* 0.5 rh))) h s 7 lay))
      (setq x (+ x w) cw (1+ cw)))
    (if (= i 0) (cld:pl (list (list (car org) (- y rh)) (list (+ (car org) tw) (- y rh))) nil (* 0.12 h) lay))
    (setq y (- y rh) i (1+ i)))
  (list (- y (* 2.0 h)) tw))
(defun cld:notes (org title lines h lay / y)
  (setq y (cadr org))
  (if (and title (/= title "")) (progn (cld:txt (list (car org) y) (* 1.3 h) title 0 lay) (setq y (- y (* 2.2 h)))))
  (foreach s lines (cld:txt (list (car org) y) h s 0 lay) (setq y (- y (* 1.7 h))))
  (- y h))

;;; ------------------------------------------------------------- oynatici
;;; Hesap motorunun urettigi cizim komutlari:
;;;  ("LY" ad renk cizgitipi kalinlik)        katman
;;;  ("I" lay blok x y aci olcek)             sembol (olcek * *cld-u*)
;;;  ("L" lay x1 y1 x2 y2)                    cizgi
;;;  ("P" lay kapali genislik ((x y) ...))    polyline
;;;  ("C" lay x y r)                          daire
;;;  ("D" lay x y r)                          dolu daire
;;;  ("T" lay x y h hiza "yazi")              yazi
;;;  ("TB" lay x y h "baslik" satirlar)       tablo
;;;  ("NT" lay x y h "baslik" satirlar)       not blogu
(defun cld:op (o / k)
  (setq k (car o))
  (cond ((= k "I") (entmake (cld:e-ins (nth 2 o) (list (nth 3 o) (nth 4 o)) (* (nth 6 o) *cld-u*) (nth 5 o) (nth 1 o))))
        ((= k "L") (cld:line (list (nth 2 o) (nth 3 o)) (list (nth 4 o) (nth 5 o)) (nth 1 o)))
        ((= k "P") (cld:pl (nth 4 o) (nth 2 o) (nth 3 o) (nth 1 o)))
        ((= k "C") (entmake (cld:e-circle (list (nth 2 o) (nth 3 o)) (nth 4 o) (nth 1 o))))
        ((= k "D") (entmake (cld:e-dot (list (nth 2 o) (nth 3 o)) (nth 4 o) (nth 1 o))))
        ((= k "T") (cld:txt (list (nth 2 o) (nth 3 o)) (nth 4 o) (nth 6 o) (nth 5 o) (nth 1 o)))
        ((= k "TB") (cld:table (list (nth 2 o) (nth 3 o)) (nth 5 o) (nth 6 o) (nth 4 o) (nth 1 o)))
        ((= k "NT") (cld:notes (list (nth 2 o) (nth 3 o)) (nth 5 o) (nth 6 o) (nth 4 o) (nth 1 o)))
        ((= k "LY") (cld:lay (nth 1 o) (nth 2 o) (nth 3 o) (nth 4 o)))
        ((= k "BK") (cld:defblk-bg (nth 1 o) (nth 2 o) (nth 3 o)))))
(defun cld:play (ops / r)
  (foreach o ops
    (setq r (vl-catch-all-apply 'cld:op (list o)))
    (cond ((vl-catch-all-error-p r) (setq *cld-bad* (cons (list (car o) (nth 1 o) (vl-catch-all-error-message r)) *cld-bad*)))
          ((and (null r) (or (member (car o) '("I" "L" "C" "D" "T")) (and (= (car o) "P") (cdr (nth 4 o)))))
           (setq *cld-bad* (cons (list (car o) (nth 1 o) (if (= (car o) "I") (nth 2 o) "")) *cld-bad*)))
          (T (setq *cld-n* (1+ *cld-n*))))))

;;; ------------------------------------------------------- calisma ortami
(defun cld:clear (pat / ss i n)
  (setq n 0)
  (if (setq ss (ssget "_X" (list (cons 8 pat))))
    (progn (setq i 0) (while (< i (sslength ss)) (entdel (ssname ss i)) (setq i (1+ i) n (1+ n)))))
  n)
(defun cld:begin (pat)
  (setq *cld-old* (list (getvar "CMDECHO") (getvar "OSMODE")) *cld-n* 0 *cld-bad* nil)
  (setvar "CMDECHO" 0)
  (setvar "OSMODE" 0)
  ;; cizim model alaninda olusur (bir yerlesim sekmesi acik olsa bile)
  (if (= 0 (getvar "TILEMODE")) (vl-catch-all-apply 'setvar (list "TILEMODE" 1)))
  (vl-catch-all-apply 'command-s (list "_.UNDO" "_BEGIN"))
  (cld:style)
  (cld:ltype "CLD_KESIK" "CLD kesik __ __" (cld:m 0.30) (cld:m 0.15))
  (cld:ltype "CLD_NOKTALI" "CLD noktali . . ." (cld:m 0.05) (cld:m 0.10))
  (cld:ltype "CLD_UZUNKESIK" "CLD uzun kesik ____ ____" (cld:m 0.80) (cld:m 0.20)))
;;; disiplin katmanlarinin kilidini kaldir / coz (eski cikti silinebilsin)
(defun cld:unlock (pat / tl ed)
  (setq tl (tblnext "LAYER" T))
  (while tl
    (if (and (wcmatch (cdr (assoc 2 tl)) pat) (/= 0 (logand 5 (cdr (assoc 70 tl)))))
      (progn (setq ed (entget (tblobjname "LAYER" (cdr (assoc 2 tl)))))
             (entmod (subst (cons 70 0) (assoc 70 ed) ed))))
    (setq tl (tblnext "LAYER"))))
(defun cld:restore ()
  (vl-catch-all-apply 'command-s (list "_.UNDO" "_END"))
  (if *cld-old* (progn (setvar "CMDECHO" (car *cld-old*)) (setvar "OSMODE" (cadr *cld-old*))))
  (setq *cld-old* nil))
(defun cld:first5 (l / r i) (setq i 0) (foreach x l (if (< i 5) (setq r (cons x r))) (setq i (1+ i))) (reverse r))
(defun cld:end (msg)
  (cld:restore)
  (princ (strcat "\n" msg " (" (itoa *cld-n*) " varlik/komut)"))
  (if *cld-bad*
    (progn
      (princ (strcat "\nCLD UYARI: " (itoa (length *cld-bad*)) " varlik olusturulamadi, ilkleri:"))
      (foreach b (cld:first5 (reverse *cld-bad*)) (princ (strcat "\n   " (vl-princ-to-string b))))))
  (princ))
;;; acik cizim baska bir parsele mi ait? (dosya adinda baska parselin "<n> NOLU" ifadesi)
(defun cld:wrong-dwg (parcel others / nm bad)
  (setq nm (strcase (getvar "DWGNAME")))
  (foreach o others (if (wcmatch nm (strcat "* " o " NOLU*,BROSCO " o " *,P" o ".DWG")) (setq bad T)))
  (and bad (not (wcmatch nm (strcat "* " parcel " NOLU*,BROSCO " parcel " *,P" parcel ".DWG")))))
(defun cld:err (m)
  (cld:restore)
  (if (not (member m '("Function cancelled" "quit / exit abort"))) (princ (strcat "\nCLD HATA: " m)))
  (princ))


;;; ==========================================================================
;;; CLD SEMBOL KUTUPHANESI - bloklar 1 birim = 1 m tanimlanir, cizime
;;; (olcek x *cld-u*) ile yerlestirilir. Duvar sembollerinde duvar yerel x=0,
;;; sembol +X yonune (mahal icine) bakar.
;;; ==========================================================================

(defun cld:b-box (w h)
  (cld:e-pl (list (list (- (/ w 2)) (- (/ h 2))) (list (/ w 2) (- (/ h 2))) (list (/ w 2) (/ h 2)) (list (- (/ w 2)) (/ h 2))) T 0.0 "0"))
(defun cld:b-wallbox (d w)
  (cld:e-pl (list (list 0.0 (- (/ w 2))) (list d (- (/ w 2))) (list d (/ w 2)) (list 0.0 (/ w 2))) T 0.0 "0"))
(defun cld:b-x (r)
  (list (cld:e-line (list (- r) (- r)) (list r r) "0") (cld:e-line (list (- r) r) (list r (- r)) "0")))
(defun cld:b-txt (p h s) (cld:e-text p h s 4 "0"))

(defun cld:def-symbols ( / r)
  ;; ---------------- AYDINLATMA
  (setq r 0.12)
  (cld:defblk "CLD_S_DL" (append (list (cld:e-circle '(0 0) r "0")) (cld:b-x (* r 0.707))))
  (cld:defblk "CLD_S_DLB" (append (list (cld:e-circle '(0 0) r "0") (cld:e-circle '(0 0) (* r 1.35) "0")) (cld:b-x (* r 0.707))))
  (cld:defblk "CLD_S_HB" (append (list (cld:e-circle '(0 0) 0.30 "0") (cld:e-circle '(0 0) 0.12 "0")) (cld:b-x 0.21)))
  (cld:defblk "CLD_S_PNL" (append (list (cld:b-box 0.6 0.6)) (cld:b-x 0.3)))
  (cld:defblk "CLD_S_ETJ" (list (cld:b-box 1.2 0.2) (cld:e-line '(-0.6 0.0) '(0.6 0.0) "0")
                                (cld:e-line '(-0.5 -0.1) '(-0.5 0.1) "0") (cld:e-line '(0.5 -0.1) '(0.5 0.1) "0")))
  (cld:defblk "CLD_S_PLF" (list (cld:e-circle '(0 0) 0.15 "0") (cld:e-dot '(0 0) 0.07 "0")))
  (cld:defblk "CLD_S_ACIL" (list (cld:b-box 0.32 0.16) (cld:e-solid '(-0.16 -0.08) '(0.16 -0.08) '(0.16 0.08) '(0.16 0.08) "0")))
  (cld:defblk "CLD_S_EXIT" (list (cld:b-box 0.40 0.20) (cld:e-line '(-0.14 0) '(0.12 0) "0") (cld:e-line '(0.12 0) '(0.04 0.06) "0")
                                 (cld:e-line '(0.12 0) '(0.04 -0.06) "0")))
  (cld:defblk "CLD_S_PRJ" (list (cld:e-pl '((-0.15 -0.10) (0.15 -0.10) (0.22 0.12) (-0.22 0.12)) T 0.0 "0") (cld:e-line '(-0.15 0.0) '(0.15 0.0) "0")))
  (cld:defblk "CLD_S_BOLLARD" (list (cld:e-circle '(0 0) 0.12 "0") (cld:e-dot '(0 0) 0.12 "0")))
  ;; ---------------- PRIZ / ANAHTAR (duvar sembolleri)
  (cld:defblk "CLD_S_PRIZ" (list (cld:e-line '(0 0) '(0.06 0) "0") (cld:e-line '(0.06 -0.12) '(0.06 0.12) "0")
                                 (cld:e-arc '(0.06 0) 0.12 (- (/ pi 2)) (/ pi 2) "0") (cld:e-line '(0.20 -0.10) '(0.20 0.10) "0")))
  (cld:defblk "CLD_S_PRIZE" (list (cld:e-line '(0 0) '(0.06 0) "0") (cld:e-line '(0.06 -0.12) '(0.06 0.12) "0")
                                  (cld:e-arc '(0.06 0) 0.12 (- (/ pi 2)) (/ pi 2) "0") (cld:e-dot '(0.11 0) 0.06 "0")
                                  (cld:e-line '(0.20 -0.10) '(0.20 0.10) "0")))
  (cld:defblk "CLD_S_PRIZU" (list (cld:e-line '(0 0) '(0.06 0) "0") (cld:e-line '(0.06 -0.12) '(0.06 0.12) "0")
                                  (cld:e-arc '(0.06 0) 0.12 (- (/ pi 2)) (/ pi 2) "0") (cld:b-txt '(0.11 0) 0.09 "U")))
  (cld:defblk "CLD_S_PRIZ3" (list (cld:e-line '(0 0) '(0.06 0) "0") (cld:e-line '(0.06 -0.14) '(0.06 0.14) "0")
                                  (cld:e-arc '(0.06 0) 0.14 (- (/ pi 2)) (/ pi 2) "0")
                                  (cld:e-line '(0.10 -0.06) '(0.18 -0.06) "0") (cld:e-line '(0.10 0.0) '(0.18 0.0) "0") (cld:e-line '(0.10 0.06) '(0.18 0.06) "0")))
  (cld:defblk "CLD_S_PGRUP" (list (cld:b-box 0.50 0.30) (cld:e-arc '(-0.13 -0.02) 0.08 0.0 pi "0") (cld:e-arc '(0.0 -0.02) 0.08 0.0 pi "0")
                                  (cld:e-arc '(0.13 -0.02) 0.08 0.0 pi "0") (cld:e-line '(-0.25 -0.08) '(0.25 -0.08) "0")))
  (foreach c '(("CLD_S_CK_KLIMA" "K") ("CLD_S_CK_FIRIN" "F") ("CLD_S_CK_BULASIK" "B") ("CLD_S_CK_CAMASIR" "\\U+00C7")
               ("CLD_S_CK_KURUTMA" "KM") ("CLD_S_CK_KOMBI" "KB") ("CLD_S_CK_DAVLUMBAZ" "D") ("CLD_S_CK_POMPA" "P")
               ("CLD_S_CK_ASPIRATOR" "A") ("CLD_S_CK_ASANSOR" "AS") ("CLD_S_CK_SARJ" "EV") ("CLD_S_CK_ISITICI" "IS")
               ("CLD_S_CK_TERMOSIFON" "TS") ("CLD_S_CK_MAKINE" "M"))
    (cld:defblk (car c) (list (cld:b-wallbox 0.24 0.24) (cld:e-solid '(0 -0.12) '(0.08 -0.12) '(0.08 0.12) '(0 0.12) "0")
                              (cld:b-txt '(0.16 0.0) 0.09 (cadr c)))))
  (cld:defblk "CLD_S_ANH1" (list (cld:e-circle '(0.10 0) 0.05 "0") (cld:e-line '(0.135 0.035) '(0.25 0.15) "0") (cld:e-line '(0.25 0.15) '(0.29 0.11) "0")))
  (cld:defblk "CLD_S_ANH2" (list (cld:e-circle '(0.10 0) 0.05 "0") (cld:e-line '(0.135 0.035) '(0.25 0.15) "0") (cld:e-line '(0.25 0.15) '(0.29 0.11) "0")
                                 (cld:e-line '(0.135 -0.035) '(0.25 -0.15) "0") (cld:e-line '(0.25 -0.15) '(0.29 -0.11) "0")))
  (cld:defblk "CLD_S_VAV" (list (cld:e-circle '(0.10 0) 0.05 "0") (cld:e-line '(0.135 0.035) '(0.25 0.15) "0") (cld:e-line '(0.25 0.15) '(0.29 0.11) "0")
                                (cld:e-line '(0.065 -0.035) '(-0.05 -0.15) "0") (cld:e-line '(-0.05 -0.15) '(-0.09 -0.11) "0")))
  (cld:defblk "CLD_S_BUAT" (list (cld:e-circle '(0 0) 0.05 "0")))
  ;; ---------------- PANOLAR
  (cld:defblk "CLD_S_TP" (list (cld:b-wallbox 0.16 0.50) (cld:e-solid '(0 -0.25) '(0.16 -0.25) '(0.16 0.25) '(0 -0.25) "0")))
  (cld:defblk "CLD_S_ADP" (list (cld:b-wallbox 0.30 0.90) (cld:e-solid '(0 -0.45) '(0.30 -0.45) '(0.30 0.45) '(0 0.45) "0")))
  (cld:defblk "CLD_S_KMP" (list (cld:b-wallbox 0.30 0.60) (cld:e-line '(0 -0.30) '(0.30 0.30) "0") (cld:b-txt '(0.15 -0.15) 0.10 "C")))
  (cld:defblk "CLD_S_KOLON" (list (cld:e-circle '(0 0) 0.15 "0") (cld:e-line '(-0.106 -0.106) '(0.106 0.106) "0")
                                  (cld:e-line '(0.106 0.106) '(0.02 0.106) "0") (cld:e-line '(0.106 0.106) '(0.106 0.02) "0")))
  (cld:defblk "CLD_S_OAP" (list (cld:b-wallbox 0.20 0.60) (cld:e-solid '(0 -0.30) '(0.20 -0.30) '(0.20 0.0) '(0 0.0) "0")))
  (cld:defblk "CLD_S_TRAFO" (list (cld:b-box 6.0 5.0) (cld:e-circle '(-0.45 0) 0.8 "0") (cld:e-circle '(0.45 0) 0.8 "0")))
  (cld:defblk "CLD_S_JEN" (list (cld:b-box 4.0 1.6) (cld:e-circle '(-1.2 0) 0.55 "0") (cld:b-txt '(-1.2 0) 0.5 "G")))
  ;; ---------------- TOPRAKLAMA / PARATONER
  (cld:defblk "CLD_S_TOP_FILIZ" (list (cld:e-circle '(0 0) 0.15 "0") (cld:e-dot '(0 0) 0.12 "0")))
  (cld:defblk "CLD_S_TOP_EPB" (list (cld:b-box 0.60 0.16) (cld:e-solid '(-0.30 -0.08) '(0.30 -0.08) '(0.30 0.08) '(-0.30 0.08) "0")
                                    (cld:e-line '(-0.2 -0.08) '(-0.2 -0.25) "0") (cld:e-line '(0 -0.08) '(0 -0.25) "0") (cld:e-line '(0.2 -0.08) '(0.2 -0.25) "0")))
  (cld:defblk "CLD_S_TOP_YEB" (list (cld:b-wallbox 0.10 0.30) (cld:e-solid '(0 -0.15) '(0.10 -0.15) '(0.10 0.15) '(0 0.15) "0")))
  (cld:defblk "CLD_S_TOP_KAZIK" (list (cld:e-line '(0 0.20) '(0 0) "0") (cld:e-line '(-0.15 0) '(0.15 0) "0")
                                      (cld:e-line '(-0.10 -0.05) '(0.10 -0.05) "0") (cld:e-line '(-0.05 -0.10) '(0.05 -0.10) "0")
                                      (cld:e-circle '(0 0.05) 0.25 "0")))
  (cld:defblk "CLD_S_TOP_OLCU" (append (list (cld:b-box 0.30 0.30)) (cld:b-x 0.15)))
  (cld:defblk "CLD_S_PAR_UC" (list (cld:e-circle '(0 0) 0.20 "0") (cld:e-solid '(-0.12 -0.08) '(0.12 -0.08) '(0.0 0.14) '(0.0 0.14) "0")))
  (cld:defblk "CLD_S_PAR_INIS" (list (cld:e-circle '(0 0) 0.15 "0") (cld:e-dot '(0 0) 0.08 "0")
                                     (cld:e-line '(0.0 -0.15) '(0.0 -0.40) "0") (cld:e-line '(-0.08 -0.30) '(0.0 -0.40) "0") (cld:e-line '(0.08 -0.30) '(0.0 -0.40) "0")))
  (cld:defblk "CLD_S_PAR_KLEMENS" (list (cld:b-box 0.25 0.25) (cld:e-solid '(-0.125 -0.125) '(0.125 -0.125) '(0.125 0.125) '(-0.125 -0.125) "0")))
  ;; ---------------- MEKANIK
  (cld:defblk "CLD_S_KASET" (append (list (cld:b-box 0.84 0.84) (cld:b-box 0.56 0.56)) (cld:b-x 0.28)))
  (cld:defblk "CLD_S_VRFOUT" (list (cld:b-box 1.30 0.75) (cld:e-circle '(-0.3 0) 0.28 "0") (cld:e-circle '(0.3 0) 0.28 "0")))
  (cld:defblk "CLD_S_HRV" (list (cld:b-box 1.40 0.80) (cld:e-line '(-0.7 -0.4) '(0.7 0.4) "0") (cld:e-line '(-0.7 0.4) '(0.7 -0.4) "0") (cld:b-txt '(0 0.25) 0.15 "HRV")))
  (cld:defblk "CLD_S_MENFEZ" (append (list (cld:b-box 0.60 0.60) (cld:b-box 0.30 0.30)) (cld:b-x 0.30)))
  (cld:defblk "CLD_S_EMIS" (list (cld:b-box 0.40 0.40) (cld:e-line '(-0.2 -0.1) '(0.2 -0.1) "0") (cld:e-line '(-0.2 0.0) '(0.2 0.0) "0") (cld:e-line '(-0.2 0.1) '(0.2 0.1) "0")))
  (cld:defblk "CLD_S_CATIFAN" (list (cld:e-circle '(0 0) 0.60 "0") (cld:e-circle '(0 0) 0.15 "0") (cld:e-line '(0 0) '(0.5 0.25) "0")
                                    (cld:e-line '(0 0) '(-0.5 0.25) "0") (cld:e-line '(0 0) '(0 -0.55) "0")))
  (cld:defblk "CLD_S_PANJUR" (list (cld:b-wallbox 0.20 1.20) (cld:e-line '(0 -0.4) '(0.2 -0.3) "0") (cld:e-line '(0 0.0) '(0.2 0.1) "0") (cld:e-line '(0 0.4) '(0.2 0.5) "0")))
  (cld:defblk "CLD_S_RADYANT" (list (cld:e-pl '((-3.0 -0.15) (3.0 -0.15) (3.0 0.15) (-3.0 0.15)) T 0.0 "0") (cld:e-line '(-3.0 0) '(2.6 0) "0") (cld:b-box 0.6 0.4)))
  (cld:defblk "CLD_S_SIGFAN" (list (cld:b-box 0.80 0.60) (cld:e-circle '(0 0) 0.22 "0") (cld:b-txt '(0 -0.2) 0.10 "S")))
  ;; ---------------- SIHHI TESISAT
  (cld:defblk "CLD_S_PK" (append (list (cld:e-circle '(0 0) 0.10 "0")) (cld:b-x 0.07)))
  (cld:defblk "CLD_S_TSK" (list (cld:e-circle '(0 0) 0.08 "0") (cld:e-dot '(0 0) 0.05 "0")))
  (cld:defblk "CLD_S_YK" (list (cld:e-circle '(0 0) 0.10 "0") (cld:e-circle '(0 0) 0.05 "0")))
  (cld:defblk "CLD_S_YS" (list (cld:b-box 0.18 0.18) (cld:e-circle '(0 0) 0.06 "0") (cld:e-line '(-0.06 0) '(0.06 0) "0")))
  (cld:defblk "CLD_S_SUSAYAC" (list (cld:e-circle '(0 0) 0.12 "0") (cld:e-line '(-0.12 0) '(0.12 0) "0") (cld:b-txt '(0 0.05) 0.06 "m3")))
  (cld:defblk "CLD_S_ROGAR" (list (cld:b-box 0.60 0.60) (cld:e-circle '(0 0) 0.22 "0")))
  (cld:defblk "CLD_S_DEPO" (append (list (cld:b-box 1.20 0.80)) (list (cld:e-line '(-0.6 -0.4) '(0.6 0.4) "0") (cld:e-line '(-0.6 0.4) '(0.6 -0.4) "0"))))
  (cld:defblk "CLD_S_KLOZET" (list (cld:e-pl '((-0.18 0.30) (0.18 0.30) (0.18 0.12) (-0.18 0.12)) T 0.0 "0")
                                   (cld:e-circle '(0 -0.08) 0.18 "0")))
  (cld:defblk "CLD_S_LAVABO" (list (cld:b-box 0.50 0.40) (cld:e-circle '(0 -0.03) 0.13 "0")))
  (cld:defblk "CLD_S_ABDEST" (list (cld:b-box 0.40 0.30) (cld:e-circle '(0 0.05) 0.05 "0") (cld:e-line '(0 0.05) '(0 -0.12) "0")))
  (cld:defblk "CLD_S_YD" (list (cld:b-wallbox 0.25 0.80) (cld:e-solid '(0 -0.40) '(0.25 -0.40) '(0.25 -0.10) '(0 -0.10) "0")
                              (cld:b-txt '(0.125 0.15) 0.12 "YD")))
  (cld:defblk "CLD_S_DUS" (append (list (cld:b-box 0.90 0.90) (cld:e-circle '(0 0) 0.06 "0")) (cld:b-x 0.45)))
  T)


(setq *cld-u* 100.0)
(setq *cld-ext* (list 0.0 0.0 1.0))

(defun cld:ops-p2_paratoner-layers () (cld:play (quote (("LY" "CLD-P2-PAR-YAZI" 7 nil -3) ("LY" "CLD-P2-PAR-PAFTA" 7 nil 50) ("LY" "CLD-P2-PAR-ALTLIK" 8 nil 13) ("LY" "CLD-P2-PAR-TABLO" 7 nil -3) ("LY" "CLD-P2-PAR-YAKALAMA" 1 nil 35) ("LY" "CLD-P2-PAR-CUBUK" 1 nil -3) ("LY" "CLD-P2-PAR-INIS" 2 "CLD_KESIK" 35) ("LY" "CLD-P2-PAR-KLEMENS" 2 nil -3)))))
(defun cld:ops-p2_paratoner-1 () (cld:play (quote (
   ("BK" "CLD_P2_MIMARI_ZK_V2" ((nil (7626.7 7918.6) (7486.7 7918.6)) (nil (7606.7 8448.2) (7606.7 7938.6)) (nil (7606.7 7938.6) (7486.7 7938.6)) (nil (7486.7 8088.6) (7596.7 8088.6)) (nil (7486.7 8113.6) (7596.7 8113.6)) (nil (7486.7 8138.6) (7596.7 8138.6)) (nil (7486.7 8163.6) (7596.7 8163.6)) (nil (7486.7 8188.6) (7596.7 8188.6)) (nil (7486.7 8213.6) (7596.7 8213.6)) (nil (7486.7 8238.6) (7596.7 8238.6)) (nil (7486.7 8263.6) (7596.7 8263.6)) (nil (7486.7 8288.6) (7596.7 8288.6)) (nil (7486.7 8313.6) (7596.7 8313.6)) (nil (7486.7 8338.6) (7606.7 8338.6)) (nil (7606.7 8063.6) (7486.7 8063.6)) (nil (7486.7 8088.6) (7606.7 8088.6)) (nil (7486.7 8113.6) (7606.7 8113.6)) (nil (7486.7 8138.6) (7606.7 8138.6)) (nil (7486.7 8163.6) (7606.7 8163.6)) (nil (7486.7 8188.6) (7606.7 8188.6)) (nil (7486.7 8213.6) (7606.7 8213.6)) (nil (7486.7 8238.6) (7606.7 8238.6)) (nil (7486.7 8263.6) (7606.7 8263.6)) (nil (7486.7 8288.6) (7606.7 8288.6)) (nil (7486.7 8313.6) (7606.7 8313.6)) (nil (7486.7 8338.6) (7603.7 8338.6)) (nil (7486.7 8063.6) (7486.7 8338.6)) (nil (7486.7 8308.6) (7486.7 8323.6)) (nil (8849.7 2070.6) (8758.3 2070.6) (6411.2 5356.7) (1582.6 6488.3) (1124.0 6935.9) (5544.5 8063.1) (6063.5 8160.0) (7235.3 8378.8) (7753.6 8475.6) (8917.5 8693.0) (8917.3 5263.4) (8917.2 2093.1)) (nil (8849.7 2063.1) (8754.5 2063.1) (6406.7 5350.0) (1578.9 6481.4) (1109.2 6939.9) (5542.9 8070.4) (6062.2 8167.4) (7233.9 8386.2) (7752.3 8483.0) (8925.0 8702.0) (8924.8 5263.4) (8924.7 2093.1)) (nil (6938.7 5245.8) (6490.4 5245.8)) (nil (6938.7 5260.8) (6479.6 5260.8)) (nil (7017.5 8286.0) (7006.6 8345.1)) (nil (7274.7 7878.9) (7274.7 7718.9)) (nil (7284.7 7868.9) (7284.7 7718.9)) (nil (7174.2 7868.8) (7174.2 7718.8)) (nil (7164.2 7868.8) (7164.2 7718.8)) (nil (7122.3 8269.1) (7106.5 8354.8)) (nil (7064.2 7868.8) (7064.2 7718.8)) (nil (7054.2 7868.8) (7054.2 7718.8)) (nil (7426.3 8063.6) (7426.3 7718.9)) (nil (7426.3 8353.6) (7426.3 8063.6)) (nil (7274.7 7878.8) (6954.2 7878.8)) (nil (7426.3 7878.9) (7274.7 7878.9)) (nil (7054.2 7868.8) (6954.2 7868.8)) (nil (7164.2 7868.8) (7064.2 7868.8)) (nil (7264.2 7868.8) (7174.2 7868.8)) (nil (7426.3 7868.9) (7284.7 7868.9)) (nil (6954.2 7718.8) (7426.3 7718.9)) (nil (7168.0 8306.1) (7168.0 8150.4)) (nil (7148.0 8302.4) (7148.0 8170.4)) (nil (6954.2 8279.2) (6954.2 7718.8)) (nil (7168.0 8150.4) (6954.2 8150.4)) (nil (7148.0 8170.4) (6954.2 8170.4)) (nil (7017.5 8286.0) (6955.0 8274.5)) (nil (7148.0 8302.4) (7117.2 8296.8)) (nil (7426.3 8353.6) (7168.0 8306.1)) (nil (6981.3 8344.4) (6894.2 8328.4)) (nil (7478.6 8424.3) (7106.5 8354.8)) (nil (6894.2 7658.8) (7486.3 7659.0)) (nil (6894.2 7658.8) (6894.2 8316.0)) (nil (7476.5 8435.6) (7476.4 8435.9)) (nil (7463.6 7658.8) (7464.9 7658.8)) (nil (6958.7 5245.8) (6958.7 6263.9)) (nil (6938.7 5245.8) (6938.7 6263.9)) (nil (1088.9 6956.1) (1090.4 6950.3)) (nil (5873.1 6746.6) (5963.8 6746.6)) (nil (5894.3 6730.4) (5894.3 6762.8)) (T (5905.1 6746.6) (5904.7 6749.4) (5903.7 6752.0) (5902.0 6754.2) (5899.7 6756.0) (5897.1 6757.0) (5894.3 6757.4) (5891.5 6757.0) (5888.9 6756.0) (5886.7 6754.2) (5885.0 6752.0) (5883.9 6749.4) (5883.5 6746.6) (5883.9 6743.8) (5885.0 6741.2) (5886.7 6739.0) (5888.9 6737.3) (5891.5 6736.2) (5894.3 6735.8) (5897.1 6736.2) (5899.7 6737.3) (5902.0 6739.0) (5903.7 6741.2) (5904.7 6743.8) (5905.1 6746.6)) (nil (8047.2 5941.3) (8137.9 5941.3)) (nil (8068.5 5925.1) (8068.5 5957.4)) (T (8079.3 5941.3) (8078.9 5944.1) (8077.8 5946.6) (8076.1 5948.9) (8073.9 5950.6) (8071.3 5951.7) (8068.5 5952.0) (8065.7 5951.7) (8063.1 5950.6) (8060.9 5948.9) (8059.1 5946.6) (8058.1 5944.1) (8057.7 5941.3) (8058.1 5938.5) (8059.1 5935.9) (8060.9 5933.6) (8063.1 5931.9) (8065.7 5930.9) (8068.5 5930.5) (8071.3 5930.9) (8073.9 5931.9) (8076.1 5933.6) (8077.8 5935.9) (8078.9 5938.5) (8079.3 5941.3)) (nil (7486.7 7658.1) (7486.7 8425.2)) (nil (6986.2 7658.1) (7486.7 7658.1)) (nil (6958.7 6923.1) (6958.7 7613.1)) (nil (6938.7 6923.1) (6938.7 7613.1)) (nil (6958.7 6323.1) (6958.7 6863.1)) (nil (6938.7 6323.1) (6938.7 6863.1)) (nil (8791.6 8677.5) (8793.3 8665.6)) (nil (8619.5 8644.9) (8621.2 8633.1)) (nil (8693.2 8659.4) (8694.9 8647.5)) (nil (8754.5 2063.1) (6406.7 5350.0) (1578.9 6481.4) (1109.2 6939.9) (5542.9 8070.4) (6062.2 8167.4) (7233.9 8386.2) (7752.3 8483.0) (8925.0 8702.0) (8924.8 5263.4) (8924.7 2093.1)) (T (1808.0 7119.5) (1805.1 7118.7) (1807.6 7109.0) (1810.5 7109.8)) (T (1811.9 7120.5) (1805.1 7118.7) (1804.6 7120.7) (1811.4 7122.4)) (T (1814.8 7108.8) (1808.0 7107.1) (1807.6 7109.0) (1814.3 7110.8)) (T (1711.1 7094.8) (1714.0 7095.5) (1716.5 7085.8) (1713.6 7085.1)) (T (1707.2 7093.8) (1714.0 7095.5) (1713.5 7097.4) (1706.7 7095.7)) (T (1710.2 7082.2) (1717.0 7083.9) (1716.5 7085.8) (1709.7 7084.1)) (T (1804.6 7120.7) (1713.5 7097.4) (1714.7 7092.6) (1805.8 7115.8)) (nil (1713.5 7097.4) (1804.6 7120.7) (1781.4 7211.8)) (nil (1713.5 7097.4) (1710.6 7121.8) (1714.1 7146.1) (1723.8 7168.7) (1738.9 7187.9) (1758.6 7202.6) (1781.4 7211.8)) (T (6288.5 8209.7) (6291.4 8210.2) (6293.3 8200.4) (6290.3 8199.8)) (T (6284.5 8208.9) (6291.4 8210.2) (6291.1 8212.2) (6284.2 8210.9)) (T (6286.8 8197.1) (6293.6 8198.4) (6293.3 8200.4) (6286.4 8199.1)) (T (6386.8 8228.0) (6383.8 8227.5) (6385.7 8217.6) (6388.6 8218.2)) (T (6390.7 8228.8) (6383.8 8227.5) (6383.5 8229.4) (6390.3 8230.7)) (T (6392.9 8217.0) (6386.0 8215.7) (6385.7 8217.6) (6392.5 8218.9)) (T (6291.1 8212.2) (6383.5 8229.4) (6384.4 8224.5) (6292.0 8207.3)) (nil (6383.5 8229.4) (6291.1 8212.2) (6273.8 8304.6)) (nil (6383.5 8229.4) (6375.9 8252.8) (6362.5 8273.3) (6344.2 8289.7) (6322.3 8300.8) (6298.3 8305.9) (6273.8 8304.6)) (T (7148.0 8175.2) (7148.0 8178.2) (7168.0 8178.2) (7168.0 8175.2)) (T (7148.0 8171.2) (7148.0 8178.2) (7146.0 8178.2) (7146.0 8171.2)) (T (7170.0 8171.2) (7170.0 8178.2) (7168.0 8178.2) (7168.0 8171.2)) (T (7148.0 8275.2) (7148.0 8272.2) (7168.0 8272.2) (7168.0 8275.2)) (T (7148.0 8279.2) (7148.0 8272.2) (7146.0 8272.2) (7146.0 8279.2)) (T (7170.0 8279.2) (7170.0 8272.2) (7168.0 8272.2) (7168.0 8279.2)) (T (7146.0 8178.2) (7146.0 8272.2) (7151.0 8272.2) (7151.0 8178.2)) (nil (7146.0 8272.2) (7146.0 8178.2) (7052.0 8178.2)) (nil (7146.0 8272.2) (7121.6 8269.0) (7099.0 8259.6) (7079.5 8244.6) (7064.6 8225.2) (7055.2 8202.5) (7052.0 8178.2)) (T (7288.7 7878.9) (7291.7 7878.9) (7291.7 7868.9) (7288.7 7868.9)) (T (7284.7 7878.9) (7291.7 7878.9) (7291.7 7880.9) (7284.7 7880.9)) (T (7284.7 7866.9) (7291.7 7866.9) (7291.7 7868.9) (7284.7 7868.9)) (T (7378.7 7878.9) (7375.7 7878.9) (7375.7 7868.9) (7378.7 7868.9)) (T (7382.7 7878.9) (7375.7 7878.9) (7375.7 7880.9) (7382.7 7880.9)) (T (7382.7 7866.9) (7375.7 7866.9) (7375.7 7868.9) (7382.7 7868.9)) (T (7291.7 7880.9) (7375.7 7880.9) (7375.7 7875.9) (7291.7 7875.9)) (nil (7375.7 7880.9) (7291.7 7880.9) (7291.7 7964.9)) (nil (7291.7 7964.9) (7313.5 7962.0) (7333.7 7953.6) (7351.1 7940.3) (7364.5 7922.9) (7372.9 7902.6) (7375.7 7880.9)) (T (7178.3 7878.8) (7181.3 7878.8) (7181.2 7868.8) (7178.2 7868.8)) (T (7174.3 7878.8) (7181.3 7878.8) (7181.3 7880.8) (7174.3 7880.8)) (T (7174.2 7866.8) (7181.2 7866.8) (7181.2 7868.8) (7174.2 7868.8)) (T (7258.2 7878.8) (7255.2 7878.8) (7255.2 7868.8) (7258.2 7868.8)) (T (7262.2 7878.8) (7255.2 7878.8) (7255.3 7880.8) (7262.3 7880.8)) (T (7262.2 7866.8) (7255.2 7866.8) (7255.2 7868.8) (7262.2 7868.8)) (T (7181.3 7880.8) (7255.3 7880.8) (7255.2 7875.8) (7181.2 7875.8)) (nil (7255.3 7880.8) (7181.3 7880.8) (7181.3 7954.8)) (nil (7181.3 7954.8) (7200.4 7952.3) (7218.3 7944.9) (7233.6 7933.1) (7245.3 7917.8) (7252.7 7900.0) (7255.3 7880.8)) (T (7068.3 7878.8) (7071.3 7878.8) (7071.2 7868.8) (7068.2 7868.8)) (T (7064.3 7878.8) (7071.3 7878.8) (7071.3 7880.8) (7064.3 7880.8)) (T (7064.2 7866.8) (7071.2 7866.8) (7071.2 7868.8) (7064.2 7868.8)) (T (7148.2 7878.8) (7145.2 7878.8) (7145.2 7868.8) (7148.2 7868.8)) (T (7152.2 7878.8) (7145.2 7878.8) (7145.3 7880.8) (7152.3 7880.8)) (T (7152.2 7866.8) (7145.2 7866.8) (7145.2 7868.8) (7152.2 7868.8)) (T (7071.3 7880.8) (7145.3 7880.8) (7145.2 7875.8) (7071.2 7875.8)) (nil (7145.3 7880.8) (7071.3 7880.8) (7071.3 7954.8)) (nil (7071.3 7954.8) (7090.4 7952.3) (7108.3 7944.9) (7123.6 7933.1) (7135.3 7917.8) (7142.7 7900.0) (7145.3 7880.8)) (T (6968.3 7878.8) (6971.3 7878.8) (6971.2 7868.8) (6968.2 7868.8)) (T (6964.3 7878.8) (6971.3 7878.8) (6971.3 7880.8) (6964.3 7880.8)) (T (6964.2 7866.8) (6971.2 7866.8) (6971.2 7868.8) (6964.2 7868.8)) (T (7048.2 7878.8) (7045.2 7878.8) (7045.2 7868.8) (7048.2 7868.8)) (T (7052.2 7878.8) (7045.2 7878.8) (7045.3 7880.8) (7052.3 7880.8)) (T (7052.2 7866.8) (7045.2 7866.8) (7045.2 7868.8) (7052.2 7868.8)) (T (6971.3 7880.8) (7045.3 7880.8) (7045.2 7875.8) (6971.2 7875.8)) (nil (7045.3 7880.8) (6971.3 7880.8) (6971.3 7954.8)) (nil (6971.3 7954.8) (6990.4 7952.3) (7008.3 7944.9) (7023.6 7933.1) (7035.3 7917.8) (7042.7 7900.0) (7045.3 7880.8)) (T (3160.7 6110.7) (3163.6 6110.0) (3165.9 6119.8) (3163.0 6120.5)) (T (3156.8 6111.7) (3163.6 6110.0) (3163.1 6108.1) (3156.3 6109.7)) (T (3159.5 6123.3) (3166.4 6121.7) (3165.9 6119.8) (3159.1 6121.4)) (T (3258.0 6087.7) (3255.1 6088.4) (3257.4 6098.1) (3260.3 6097.4)) (T (3261.9 6086.8) (3255.1 6088.4) (3254.6 6086.4) (3261.4 6084.8)) (T (3264.6 6098.5) (3257.8 6100.1) (3257.4 6098.1) (3264.2 6096.5)) (T (3163.1 6108.1) (3254.6 6086.4) (3255.8 6091.3) (3164.3 6113.0)) (nil (3254.6 6086.4) (3163.1 6108.1) (3141.5 6016.6)) (nil (3254.6 6086.4) (3245.9 6063.5) (3231.5 6043.6) (3212.5 6028.1) (3190.1 6018.1) (3165.9 6014.1) (3141.5 6016.6)) (T (4808.6 7883.2) (4805.7 7882.4) (4808.1 7872.7) (4811.0 7873.5)) (T (4812.5 7884.2) (4805.7 7882.4) (4805.2 7884.4) (4812.0 7886.1)) (T (4815.4 7872.5) (4808.6 7870.8) (4808.1 7872.7) (4814.9 7874.5)) (T (4711.7 7858.5) (4714.6 7859.2) (4717.1 7849.5) (4714.2 7848.8)) (T (4707.8 7857.5) (4714.6 7859.2) (4714.1 7861.1) (4707.3 7859.4)) (T (4710.8 7845.9) (4717.6 7847.6) (4717.1 7849.5) (4710.3 7847.8)) (T (4805.2 7884.4) (4714.1 7861.1) (4715.3 7856.3) (4806.4 7879.5)) (nil (4714.1 7861.1) (4805.2 7884.4) (4782.0 7975.5)) (nil (4714.1 7861.1) (4711.2 7885.5) (4714.7 7909.8) (4724.3 7932.4) (4739.5 7951.6) (4759.2 7966.3) (4782.0 7975.5)) (T (8791.6 8677.5) (8788.6 8676.9) (8790.4 8667.1) (8793.4 8667.6)) (T (8795.5 8678.2) (8788.6 8676.9) (8788.3 8678.9) (8795.2 8680.2)) (T (8797.7 8666.4) (8790.8 8665.1) (8790.4 8667.1) (8797.3 8668.4)) (T (8693.2 8659.4) (8696.2 8659.9) (8698.0 8650.1) (8695.0 8649.5)) (T (8689.3 8658.6) (8696.2 8659.9) (8695.8 8661.9) (8688.9 8660.6)) (T (8691.5 8646.8) (8698.4 8648.1) (8698.0 8650.1) (8691.1 8648.8)) (T (8788.3 8678.9) (8695.8 8661.9) (8696.7 8657.0) (8789.2 8674.0)) (nil (8695.8 8661.9) (8788.3 8678.9) (8771.3 8771.3)) (nil (8695.8 8661.9) (8694.6 8686.4) (8699.7 8710.4) (8710.9 8732.2) (8727.3 8750.4) (8747.9 8763.8) (8771.3 8771.3)) (T (8925.0 5530.8) (8925.0 5533.8) (8915.0 5533.8) (8915.0 5530.8)) (T (8925.0 5526.8) (8925.0 5533.8) (8927.0 5533.8) (8927.0 5526.8)) (T (8913.0 5526.8) (8913.0 5533.8) (8915.0 5533.8) (8915.0 5526.8)) (T (8925.0 5630.8) (8925.0 5627.8) (8915.0 5627.8) (8915.0 5630.8)) (T (8925.0 5634.8) (8925.0 5627.8) (8927.0 5627.8) (8927.0 5634.8)) (T (8913.0 5634.8) (8913.0 5627.8) (8915.0 5627.8) (8915.0 5634.8)) (T (8927.0 5533.8) (8927.0 5627.8) (8922.0 5627.8) (8922.0 5533.8)) (nil (8927.0 5627.8) (8927.0 5533.8) (9021.0 5533.8)) (nil (8927.0 5627.8) (8951.3 5624.6) (8974.0 5615.2) (8993.5 5600.3) (9008.4 5580.8) (9017.8 5558.1) (9021.0 5533.8)) (T (7680.6 3580.0) (7678.8 3582.4) (7670.7 3576.6) (7672.4 3574.2)) (T (7682.9 3576.7) (7678.8 3582.4) (7680.4 3583.6) (7684.5 3577.9)) (T (7673.1 3569.7) (7669.1 3575.4) (7670.7 3576.6) (7674.8 3570.9)) (T (7622.2 3661.2) (7624.0 3658.8) (7615.9 3652.9) (7614.1 3655.4)) (T (7619.9 3664.5) (7624.0 3658.8) (7625.6 3659.9) (7621.5 3665.6)) (T (7610.1 3657.5) (7614.2 3651.8) (7615.9 3652.9) (7611.8 3658.6)) (T (7680.4 3583.6) (7625.6 3659.9) (7621.5 3657.0) (7676.4 3580.7)) (nil (7625.6 3659.9) (7680.4 3583.6) (7756.8 3638.4)) (nil (7625.6 3659.9) (7647.2 3671.5) (7671.1 3677.1) (7695.7 3676.4) (7719.1 3669.3) (7740.0 3656.3) (7756.8 3638.4)) (T (6178.8 5403.4) (6181.7 5402.7) (6184.0 5412.5) (6181.1 5413.1)) (T (6174.9 5404.3) (6181.7 5402.7) (6181.3 5400.8) (6174.5 5402.4)) (T (6177.7 5416.0) (6184.5 5414.4) (6184.0 5412.5) (6177.2 5414.1)) (T (6276.1 5380.4) (6273.2 5381.1) (6275.5 5390.8) (6278.4 5390.1)) (T (6280.0 5379.5) (6273.2 5381.1) (6272.7 5379.1) (6279.6 5377.5)) (T (6282.8 5391.1) (6276.0 5392.7) (6275.5 5390.8) (6282.3 5389.2)) (T (6181.3 5400.8) (6272.7 5379.1) (6273.9 5384.0) (6182.4 5405.6)) (nil (6272.7 5379.1) (6181.3 5400.8) (6159.6 5309.3)) (nil (6272.7 5379.1) (6264.0 5356.2) (6249.7 5336.3) (6230.6 5320.8) (6208.2 5310.7) (6184.0 5306.8) (6159.6 5309.3))) ((7114.2 7814.8 22.0 "BAY WC") (7114.2 7778.8 16.0 "1,5 m\\U+00B2") (7004.2 7814.8 22.0 "BAYAN WC") (7004.2 7778.8 16.0 "1,5 m\\U+00B2") (7224.5 7814.8 22.0 "\\U+00C7\\U+00D6P ODASI") (7224.5 7778.8 16.0 "2,1 m\\U+00B2") (7032.5 8286.4 22.0 "G\\U+00DCV. HOL\\U+00DC") (7032.5 8250.4 16.0 "2,1 m\\U+00B2") (7359.3 7811.9 22.0 "JENARAT\\U+00D6R ODASI") (7359.3 7775.9 16.0 "1,5 m\\U+00B2") (7190.3 8079.4 22.0 "SI\\U+011EINAK") (7190.3 8043.4 16.0 "15,5 m\\U+00B2") (7938.0 5616.7 22.0 "\\U+00DCRET\\U+0130M ALANI") (7938.0 5580.7 16.0 "1.005,3 m\\U+00B2") (4097.1 6829.4 22.0 "\\U+00DCRET\\U+0130M ALANI") (4097.1 6793.4 16.0 "1.009,7 m\\U+00B2")))
   ("BK" "CLD_P2_MIMARI_CT_V2" ((nil (8791.2 2096.9) (8989.0 2096.9)) (nil (8780.0 2089.4) (8989.0 2089.4)) (nil (6783.1 9066.8) (6783.1 9373.4)) (nil (6783.1 2401.1) (6783.1 2069.5)) (nil (8951.3 6811.2) (9257.8 6811.2)) (nil (1467.5 6686.9) (1135.9 6686.9)) (nil (8791.2 2096.9) (6470.2 5346.3) (1642.3 6477.7) (1172.7 6936.1) (5606.3 8066.7) (6125.7 8163.7) (7297.4 8382.5) (7815.8 8479.3) (8988.5 8698.3) (8988.3 5259.7) (8988.1 2099.8)) (nil (8683.0 8641.2) (8684.7 8629.3))) ())
   ("T" "CLD-P2-PAR-YAZI" 97243.5 -115805.9 160.0 0 "PARSEL 2 - PARATONER (YILDIRIMDAN KORUNMA) PROJES\\U+0130")
   ("T" "CLD-P2-PAR-YAZI" 97243.5 -116035.9 50.0 0 "BROSCO \\U+0130THALAT \\U+0130HRACAT VE T\\U+0130CARET ANON\\U+0130M \\U+015E\\U+0130RKET\\U+0130 - YUKARI MAHALLE / KEMALPA\\U+015EA / \\U+0130ZM\\U+0130R")
   ("T" "CLD-P2-PAR-YAZI" 97243.5 -116115.9 38.0 0 "CLD otomatik proje  |  Disiplin 03  |  19.10.2026  |  Paftalar 1/100  |  Katman \\U+00F6neki CLD-P2-PAR-*")
   ("I" "CLD-P2-PAR-ALTLIK" "CLD_P2_MIMARI_CT_V2" 97243.5 -126532.3 0.0 0.01)
   ("T" "CLD-P2-PAR-TABLO" 107255.4 -116455.9 26.0 0 "LEJANT")
   ("P" "CLD-P2-PAR-TABLO" T 0.0 ((107255.4 -116475.9) (108309.0 -116475.9) (108309.0 -116687.9) (107255.4 -116687.9)))
   ("P" "CLD-P2-PAR-YAKALAMA" nil 0.0 ((107275.4 -116517.9) (107475.4 -116517.9)))
   ("T" "CLD-P2-PAR-TABLO" 107495.4 -116517.9 20.0 7 "Yakalama iletkeni \\U+00D88 mm Al/galvaniz, klips aral\\U+0131\\U+011F\\U+0131 1 m")
   ("I" "CLD-P2-PAR-TABLO" "CLD_S_PAR_UC" 107375.4 -116581.9 0.0 1.3)
   ("T" "CLD-P2-PAR-TABLO" 107495.4 -116581.9 20.0 7 "Yakalama \\U+00E7ubu\\U+011Fu: k\\U+00F6\\U+015Fe / mahya h=1,0 m, \\U+00E7at\\U+0131 fan\\U+0131 yan\\U+0131nda h=1,5 m")
   ("I" "CLD-P2-PAR-TABLO" "CLD_S_PAR_INIS" 107375.4 -116645.9 0.0 0.945)
   ("T" "CLD-P2-PAR-TABLO" 107495.4 -116645.9 20.0 7 "\\U+0130ni\\U+015F iletkeni \\U+00D88 mm (veya s\\U+00FCreklili\\U+011Fi sa\\U+011Flanm\\U+0131\\U+015F \\U+00E7elik kolon)")
   ("P" "CLD-P2-PAR-PAFTA" nil 6.0 ((107105.4 -126552.3) (107105.4 -116305.9)))
   ("P" "CLD-P2-PAR-PAFTA" T 10.0 ((97143.5 -127232.3) (108559.0 -127232.3) (108559.0 -116305.9) (97143.5 -116305.9)))
   ("P" "CLD-P2-PAR-PAFTA" nil 6.0 ((97143.5 -126552.3) (108559.0 -126552.3)))
   ("P" "CLD-P2-PAR-PAFTA" T 6.0 ((106059.0 -127232.3) (108559.0 -127232.3) (108559.0 -126552.3) (106059.0 -126552.3)))
   ("T" "CLD-P2-PAR-YAZI" 106089.0 -126615.5 18.0 0 "\\U+0130\\U+015E\\U+0130N ADI")
   ("T" "CLD-P2-PAR-YAZI" 106679.0 -126615.5 20.0 0 "PARATONER (YILDIRIMDAN KORUNMA) PROJES\\U+0130")
   ("L" "CLD-P2-PAR-PAFTA" 106059.0 -126649.5 108559.0 -126649.5)
   ("T" "CLD-P2-PAR-YAZI" 106089.0 -126712.6 18.0 0 "YAPI SAH\\U+0130B\\U+0130")
   ("T" "CLD-P2-PAR-YAZI" 106679.0 -126712.6 20.0 0 "BROSCO \\U+0130THALAT \\U+0130HRACAT VE T\\U+0130CARET ANON\\U+0130M \\U+015E\\U+0130RKET\\U+0130")
   ("L" "CLD-P2-PAR-PAFTA" 106059.0 -126746.6 108559.0 -126746.6)
   ("T" "CLD-P2-PAR-YAZI" 106089.0 -126809.8 18.0 0 "ADRES")
   ("T" "CLD-P2-PAR-YAZI" 106679.0 -126809.8 20.0 0 "YUKARI MAHALLE / KEMALPA\\U+015EA / \\U+0130ZM\\U+0130R  -  Ada: ......  Parsel: 2")
   ("L" "CLD-P2-PAR-PAFTA" 106059.0 -126843.8 108559.0 -126843.8)
   ("T" "CLD-P2-PAR-YAZI" 106089.0 -126906.9 18.0 0 "PAFTA ADI")
   ("T" "CLD-P2-PAR-YAZI" 106679.0 -126906.9 20.0 0 "\\U+00C7ATI YAKALAMA S\\U+0130STEM\\U+0130 (Faraday a\\U+011F\\U+0131 5x5 m, LPL I) - \\U+00C7ATI PLANI")
   ("L" "CLD-P2-PAR-PAFTA" 106059.0 -126940.9 108559.0 -126940.9)
   ("T" "CLD-P2-PAR-YAZI" 106089.0 -127004.1 18.0 0 "\\U+00D6L\\U+00C7EK / TAR\\U+0130H / PAFTA NO")
   ("T" "CLD-P2-PAR-YAZI" 106679.0 -127004.1 20.0 0 "1/100   |   19.10.2026   |   03-01")
   ("L" "CLD-P2-PAR-PAFTA" 106059.0 -127038.1 108559.0 -127038.1)
   ("T" "CLD-P2-PAR-YAZI" 106089.0 -127101.2 18.0 0 "PROJE M\\U+00DCELL\\U+0130F\\U+0130")
   ("T" "CLD-P2-PAR-YAZI" 106679.0 -127101.2 20.0 0 "Elektrik M\\U+00FChendisi - Ad\\U+0131 Soyad\\U+0131: ..............................")
   ("L" "CLD-P2-PAR-PAFTA" 106059.0 -127135.2 108559.0 -127135.2)
   ("T" "CLD-P2-PAR-YAZI" 106089.0 -127198.3 18.0 0 "ODA S\\U+0130C\\U+0130L / SMM NO")
   ("T" "CLD-P2-PAR-YAZI" 106679.0 -127198.3 20.0 0 "EMO Sicil No: ............   SMM Belge No: ............   \\U+0130mza: ............")
   ("L" "CLD-P2-PAR-PAFTA" 106649.0 -127232.3 106649.0 -126552.3)
   ("T" "CLD-P2-PAR-YAZI" 97243.5 -126692.3 70.0 0 "\\U+00C7ATI YAKALAMA S\\U+0130STEM\\U+0130 (Faraday a\\U+011F\\U+0131 5x5 m, LPL I)")
   ("T" "CLD-P2-PAR-YAZI" 97243.5 -126832.3 40.0 0 "\\U+00C7ATI PLANI  -  \\U+00D6: 1/100")
   ("T" "CLD-P2-PAR-YAZI" 97243.5 -126932.3 30.0 0 "Parsel 2  |  BROSCO \\U+0130THALAT \\U+0130HRACAT VE T\\U+0130CARET ANON\\U+0130M \\U+015E\\U+0130RKET\\U+0130")
   ("T" "CLD-P2-PAR-YAZI" 97243.5 -127012.3 26.0 0 "CLD - 19.10.2026 - mimari altl\\U+0131k: BROSCO 2 NOLU PARSEL M\\U+0130MAR\\U+0130.dwg")
   ("P" "CLD-P2-PAR-YAKALAMA" T 6.0 ((98358.2 -119580.3) (102835.3 -118438.6) (104168.9 -118189.1) (104223.7 -118173.2) (104316.7 -118161.5) (106261.9 -117798.2) (106261.5 -124805.1) (103800.2 -121359.2) (103677.5 -121240.1) (103520.7 -121172.0) (98941.4 -120098.7) (98818.8 -120031.5) (98358.2 -119580.3)))
   ("P" "CLD-P2-PAR-YAKALAMA" nil 4.0 ((105780.4 -117908.5) (105780.1 -124096.7)))
   ("P" "CLD-P2-PAR-YAKALAMA" nil 4.0 ((105319.0 -117994.6) (105318.7 -123450.8)))
   ("P" "CLD-P2-PAR-YAKALAMA" nil 4.0 ((104857.6 -118080.8) (104857.3 -122804.8)))
   ("P" "CLD-P2-PAR-YAKALAMA" nil 4.0 ((104396.1 -118167.0) (104395.9 -122158.9)))
   ("P" "CLD-P2-PAR-YAKALAMA" nil 4.0 ((103934.7 -118253.2) (103934.5 -121512.9)))
   ("P" "CLD-P2-PAR-YAKALAMA" nil 4.0 ((103473.3 -118339.6) (103473.3 -119099.1) (103475.8 -119107.6) (103478.4 -119116.0) (103480.1 -119124.7) (103481.0 -119133.5) (103481.8 -119142.3) (103481.0 -119151.2) (103480.1 -119160.0) (103478.4 -119168.7) (103475.8 -119177.1) (103473.2 -119185.6) (103473.1 -121140.3)))
   ("P" "CLD-P2-PAR-YAKALAMA" nil 4.0 ((103011.9 -118425.9) (103011.7 -121032.1)))
   ("P" "CLD-P2-PAR-YAKALAMA" nil 4.0 ((102550.4 -118531.9) (102550.3 -120924.0)))
   ("P" "CLD-P2-PAR-YAKALAMA" nil 4.0 ((102089.0 -118649.6) (102088.9 -120815.9)))
   ("P" "CLD-P2-PAR-YAKALAMA" nil 4.0 ((101627.6 -118767.2) (101627.5 -120707.7)))
   ("P" "CLD-P2-PAR-YAKALAMA" nil 4.0 ((101166.2 -118884.9) (101166.1 -120599.6)))
   ("P" "CLD-P2-PAR-YAKALAMA" nil 4.0 ((100704.7 -119002.6) (100704.6 -120491.4)))
   ("P" "CLD-P2-PAR-YAKALAMA" nil 4.0 ((100243.3 -119120.2) (100243.2 -120383.3)))
   ("P" "CLD-P2-PAR-YAKALAMA" nil 4.0 ((99781.9 -119237.9) (99781.8 -120275.2)))
   ("P" "CLD-P2-PAR-YAKALAMA" nil 4.0 ((99320.4 -119355.5) (99320.4 -120167.0)))
   ("P" "CLD-P2-PAR-YAKALAMA" nil 4.0 ((98859.0 -119473.2) (98859.0 -120030.7)))
   ("P" "CLD-P2-PAR-YAKALAMA" nil 4.0 ((106241.8 -118283.6) (103772.9 -118283.5)))
   ("P" "CLD-P2-PAR-YAKALAMA" nil 4.0 ((106241.8 -118745.0) (101715.7 -118744.8)))
   ("P" "CLD-P2-PAR-YAKALAMA" nil 4.0 ((106241.8 -119206.4) (103462.0 -119206.2) (103447.9 -119223.1) (103430.8 -119236.9) (103411.4 -119247.2) (103390.4 -119253.6) (103368.5 -119255.7) (103346.6 -119253.6) (103325.5 -119247.2) (103306.1 -119236.9) (103289.0 -119223.1) (103274.9 -119206.2) (99906.8 -119206.0)))
   ("P" "CLD-P2-PAR-YAKALAMA" nil 4.0 ((106241.8 -119667.7) (98475.6 -119667.3)))
   ("P" "CLD-P2-PAR-YAKALAMA" nil 4.0 ((106241.7 -120129.1) (99156.8 -120128.7)))
   ("P" "CLD-P2-PAR-YAKALAMA" nil 4.0 ((106241.7 -120590.4) (103753.1 -120590.3) (103741.6 -120563.7) (103723.7 -120540.9) (103700.3 -120523.8) (103673.5 -120512.9) (103644.8 -120508.7) (103616.1 -120512.9) (103589.3 -120523.8) (103565.9 -120540.9) (103548.0 -120563.7) (103536.5 -120590.3) (101125.9 -120590.2)))
   ("P" "CLD-P2-PAR-YAKALAMA" nil 4.0 ((106241.7 -121051.8) (103094.9 -121051.6)))
   ("P" "CLD-P2-PAR-YAKALAMA" nil 4.0 ((106241.7 -121513.2) (103934.6 -121513.0)))
   ("P" "CLD-P2-PAR-YAKALAMA" nil 4.0 ((106241.6 -121974.5) (104264.2 -121974.4)))
   ("P" "CLD-P2-PAR-YAKALAMA" nil 4.0 ((106241.6 -122435.9) (104593.7 -122435.8)))
   ("P" "CLD-P2-PAR-YAKALAMA" nil 4.0 ((106241.6 -122897.2) (104923.3 -122897.2)))
   ("P" "CLD-P2-PAR-YAKALAMA" nil 4.0 ((106241.6 -123358.6) (105252.8 -123358.5)))
   ("P" "CLD-P2-PAR-YAKALAMA" nil 4.0 ((106241.5 -123819.9) (105582.4 -123819.9)))
   ("P" "CLD-P2-PAR-YAKALAMA" nil 4.0 ((106241.5 -124281.3) (105911.9 -124281.3)))
   ("I" "CLD-P2-PAR-CUBUK" "CLD_S_PAR_UC" 98417.3 -119596.2 0.0 2.5)
   ("I" "CLD-P2-PAR-CUBUK" "CLD_S_PAR_UC" 106231.9 -117834.3 0.0 2.5)
   ("I" "CLD-P2-PAR-CUBUK" "CLD_S_PAR_UC" 106231.5 -124711.5 0.0 2.5)
   ("I" "CLD-P2-PAR-CUBUK" "CLD_S_PAR_UC" 103694.5 -121214.8 0.0 2.5)
   ("I" "CLD-P2-PAR-CUBUK" "CLD_S_PAR_UC" 98952.2 -120070.5 0.0 2.5)
   ("I" "CLD-P2-PAR-CUBUK" "CLD_S_PAR_UC" 99296.6 -119341.0 0.0 2.5)
   ("I" "CLD-P2-PAR-CUBUK" "CLD_S_PAR_UC" 100234.9 -119101.7 0.0 2.5)
   ("I" "CLD-P2-PAR-CUBUK" "CLD_S_PAR_UC" 101173.3 -118862.4 0.0 2.5)
   ("I" "CLD-P2-PAR-CUBUK" "CLD_S_PAR_UC" 102111.6 -118623.2 0.0 2.5)
   ("I" "CLD-P2-PAR-CUBUK" "CLD_S_PAR_UC" 103053.1 -118397.9 0.0 2.5)
   ("I" "CLD-P2-PAR-CUBUK" "CLD_S_PAR_UC" 104005.0 -118219.7 0.0 2.5)
   ("I" "CLD-P2-PAR-CUBUK" "CLD_S_PAR_UC" 104956.4 -118042.0 0.0 2.5)
   ("I" "CLD-P2-PAR-CUBUK" "CLD_S_PAR_UC" 105908.4 -117864.2 0.0 2.5)
   ("I" "CLD-P2-PAR-CUBUK" "CLD_S_PAR_UC" 106261.8 -118407.0 0.0 2.5)
   ("I" "CLD-P2-PAR-CUBUK" "CLD_S_PAR_UC" 106261.8 -119375.4 0.0 2.5)
   ("I" "CLD-P2-PAR-CUBUK" "CLD_S_PAR_UC" 106261.7 -120343.8 0.0 2.5)
   ("I" "CLD-P2-PAR-CUBUK" "CLD_S_PAR_UC" 106261.7 -121312.2 0.0 2.5)
   ("I" "CLD-P2-PAR-CUBUK" "CLD_S_PAR_UC" 106261.6 -122280.6 0.0 2.5)
   ("I" "CLD-P2-PAR-CUBUK" "CLD_S_PAR_UC" 106261.6 -123249.0 0.0 2.5)
   ("I" "CLD-P2-PAR-CUBUK" "CLD_S_PAR_UC" 106261.5 -124217.3 0.0 2.5)
   ("I" "CLD-P2-PAR-CUBUK" "CLD_S_PAR_UC" 105477.4 -123707.3 0.0 2.5)
   ("I" "CLD-P2-PAR-CUBUK" "CLD_S_PAR_UC" 104914.5 -122919.3 0.0 2.5)
   ("I" "CLD-P2-PAR-CUBUK" "CLD_S_PAR_UC" 104351.6 -122131.3 0.0 2.5)
   ("I" "CLD-P2-PAR-CUBUK" "CLD_S_PAR_UC" 102891.7 -121024.5 0.0 2.5)
   ("I" "CLD-P2-PAR-CUBUK" "CLD_S_PAR_UC" 101948.8 -120803.6 0.0 2.5)
   ("I" "CLD-P2-PAR-CUBUK" "CLD_S_PAR_UC" 101006.0 -120582.6 0.0 2.5)
   ("I" "CLD-P2-PAR-CUBUK" "CLD_S_PAR_UC" 100063.2 -120361.6 0.0 2.5)
   ("I" "CLD-P2-PAR-CUBUK" "CLD_S_PAR_UC" 105497.6 -118508.9 0.0 2.5)
   ("I" "CLD-P2-PAR-CUBUK" "CLD_S_PAR_UC" 105737.6 -118508.9 0.0 2.5)
   ("I" "CLD-P2-PAR-CUBUK" "CLD_S_PAR_UC" 105497.5 -119839.9 0.0 2.5)
   ("I" "CLD-P2-PAR-CUBUK" "CLD_S_PAR_UC" 105737.5 -119839.9 0.0 2.5)
   ("I" "CLD-P2-PAR-CUBUK" "CLD_S_PAR_UC" 105497.4 -121171.0 0.0 2.5)
   ("I" "CLD-P2-PAR-CUBUK" "CLD_S_PAR_UC" 105737.4 -121171.0 0.0 2.5)
   ("I" "CLD-P2-PAR-CUBUK" "CLD_S_PAR_UC" 103524.8 -120622.1 0.0 2.5)
   ("I" "CLD-P2-PAR-CUBUK" "CLD_S_PAR_UC" 103764.8 -120622.1 0.0 2.5)
   ("I" "CLD-P2-PAR-CUBUK" "CLD_S_PAR_UC" 101306.9 -119504.9 0.0 2.5)
   ("I" "CLD-P2-PAR-CUBUK" "CLD_S_PAR_UC" 101546.9 -119504.9 0.0 2.5)
   ("I" "CLD-P2-PAR-CUBUK" "CLD_S_PAR_UC" 103248.5 -119142.3 0.0 2.5)
   ("I" "CLD-P2-PAR-CUBUK" "CLD_S_PAR_UC" 103488.5 -119142.3 0.0 2.5)
   ("P" "CLD-P2-PAR-YAKALAMA" nil 4.0 ((105319.0 -118508.8) (105497.6 -118508.9)))
   ("P" "CLD-P2-PAR-YAKALAMA" nil 4.0 ((105780.4 -118508.9) (105737.6 -118508.9)))
   ("P" "CLD-P2-PAR-YAKALAMA" nil 4.0 ((105497.5 -119667.7) (105497.5 -119839.9)))
   ("P" "CLD-P2-PAR-YAKALAMA" nil 4.0 ((105780.3 -119839.9) (105737.5 -119839.9)))
   ("P" "CLD-P2-PAR-YAKALAMA" nil 4.0 ((105497.4 -121051.8) (105497.4 -121171.0)))
   ("P" "CLD-P2-PAR-YAKALAMA" nil 4.0 ((105780.3 -121171.0) (105737.4 -121171.0)))
   ("P" "CLD-P2-PAR-YAKALAMA" nil 4.0 ((103524.8 -120590.3) (103524.8 -120622.1)))))))
(defun cld:ops-p2_paratoner-2 () (cld:play (quote (
   ("P" "CLD-P2-PAR-YAKALAMA" nil 4.0 ((103764.8 -120590.3) (103764.8 -120622.1)))
   ("P" "CLD-P2-PAR-YAKALAMA" nil 4.0 ((101166.1 -119504.9) (101306.9 -119504.9)))
   ("P" "CLD-P2-PAR-YAKALAMA" nil 4.0 ((101627.5 -119504.9) (101546.9 -119504.9)))
   ("P" "CLD-P2-PAR-YAKALAMA" nil 4.0 ((103248.5 -119206.2) (103248.5 -119142.3)))
   ("P" "CLD-P2-PAR-YAKALAMA" nil 4.0 ((103481.8 -119142.3) (103488.5 -119142.3)))
   ("I" "CLD-P2-PAR-INIS" "CLD_S_PAR_INIS" 98417.3 -119596.2 0.0 2.5)
   ("I" "CLD-P2-PAR-INIS" "CLD_S_PAR_INIS" 99280.3 -119376.1 0.0 2.5)
   ("I" "CLD-P2-PAR-INIS" "CLD_S_PAR_INIS" 100143.2 -119156.1 0.0 2.5)
   ("I" "CLD-P2-PAR-INIS" "CLD_S_PAR_INIS" 101006.2 -118936.0 0.0 2.5)
   ("I" "CLD-P2-PAR-INIS" "CLD_S_PAR_INIS" 101869.2 -118716.0 0.0 2.5)
   ("I" "CLD-P2-PAR-INIS" "CLD_S_PAR_INIS" 102732.1 -118495.9 0.0 2.5)
   ("I" "CLD-P2-PAR-INIS" "CLD_S_PAR_INIS" 103558.3 -118333.9 0.0 2.5)
   ("I" "CLD-P2-PAR-INIS" "CLD_S_PAR_INIS" 104480.9 -118161.3 0.0 2.5)
   ("I" "CLD-P2-PAR-INIS" "CLD_S_PAR_INIS" 105356.4 -117997.8 0.0 2.5)
   ("I" "CLD-P2-PAR-INIS" "CLD_S_PAR_INIS" 106231.9 -117834.3 0.0 2.5)
   ("I" "CLD-P2-PAR-INIS" "CLD_S_PAR_INIS" 106231.8 -118816.8 0.0 2.5)
   ("I" "CLD-P2-PAR-INIS" "CLD_S_PAR_INIS" 106231.7 -119799.2 0.0 2.5)
   ("I" "CLD-P2-PAR-INIS" "CLD_S_PAR_INIS" 106231.7 -120781.7 0.0 2.5)
   ("I" "CLD-P2-PAR-INIS" "CLD_S_PAR_INIS" 106231.6 -121764.1 0.0 2.5)
   ("I" "CLD-P2-PAR-INIS" "CLD_S_PAR_INIS" 106231.6 -122746.6 0.0 2.5)
   ("I" "CLD-P2-PAR-INIS" "CLD_S_PAR_INIS" 106231.5 -123729.0 0.0 2.5)
   ("I" "CLD-P2-PAR-INIS" "CLD_S_PAR_INIS" 106231.5 -124711.5 0.0 2.5)
   ("I" "CLD-P2-PAR-INIS" "CLD_S_PAR_INIS" 105729.0 -124007.9 0.0 2.5)
   ("I" "CLD-P2-PAR-INIS" "CLD_S_PAR_INIS" 105226.4 -123304.4 0.0 2.5)
   ("I" "CLD-P2-PAR-INIS" "CLD_S_PAR_INIS" 104723.9 -122600.9 0.0 2.5)
   ("I" "CLD-P2-PAR-INIS" "CLD_S_PAR_INIS" 104221.4 -121897.3 0.0 2.5)
   ("I" "CLD-P2-PAR-INIS" "CLD_S_PAR_INIS" 103694.5 -121214.8 0.0 2.5)
   ("I" "CLD-P2-PAR-INIS" "CLD_S_PAR_INIS" 102754.1 -120961.5 0.0 2.5)
   ("I" "CLD-P2-PAR-INIS" "CLD_S_PAR_INIS" 101803.6 -120738.7 0.0 2.5)
   ("I" "CLD-P2-PAR-INIS" "CLD_S_PAR_INIS" 100853.2 -120516.0 0.0 2.5)
   ("I" "CLD-P2-PAR-INIS" "CLD_S_PAR_INIS" 99902.7 -120293.2 0.0 2.5)
   ("I" "CLD-P2-PAR-INIS" "CLD_S_PAR_INIS" 98952.2 -120070.5 0.0 2.5)
   ("T" "CLD-P2-PAR-YAZI" 105557.6 -118448.9 18.0 0 "\\U+00E7at\\U+0131 fan\\U+0131 yan\\U+0131nda yakalama \\U+00E7ubu\\U+011Fu h=1,5 m, a\\U+011Fa ba\\U+011Fl\\U+0131 (s \\U+2265 0,48 m)")
   ("I" "CLD-P2-PAR-ALTLIK" "CLD_P2_MIMARI_ZK_V2" 109659.0 -126532.3 0.0 0.01)
   ("T" "CLD-P2-PAR-TABLO" 119740.8 -116455.9 26.0 0 "LEJANT")
   ("P" "CLD-P2-PAR-TABLO" T 0.0 ((119740.8 -116475.9) (120744.8 -116475.9) (120744.8 -116623.9) (119740.8 -116623.9)))
   ("I" "CLD-P2-PAR-TABLO" "CLD_S_PAR_INIS" 119860.8 -116517.9 0.0 0.945)
   ("T" "CLD-P2-PAR-TABLO" 119980.8 -116517.9 20.0 7 "\\U+0130ni\\U+015F iletkeni \\U+00D88 mm (veya s\\U+00FCreklili\\U+011Fi sa\\U+011Flanm\\U+0131\\U+015F \\U+00E7elik kolon)")
   ("I" "CLD-P2-PAR-TABLO" "CLD_S_PAR_KLEMENS" 119860.8 -116581.9 0.0 1.733)
   ("T" "CLD-P2-PAR-TABLO" 119980.8 -116581.9 20.0 7 "\\U+00D6l\\U+00E7\\U+00FC (ay\\U+0131rma) klemensi h=0,5 m, temel topraklamas\\U+0131na ba\\U+011Fl\\U+0131")
   ("P" "CLD-P2-PAR-PAFTA" nil 6.0 ((119590.8 -126552.3) (119590.8 -116305.9)))
   ("P" "CLD-P2-PAR-PAFTA" T 10.0 ((109559.0 -127232.3) (120994.8 -127232.3) (120994.8 -116305.9) (109559.0 -116305.9)))
   ("P" "CLD-P2-PAR-PAFTA" nil 6.0 ((109559.0 -126552.3) (120994.8 -126552.3)))
   ("P" "CLD-P2-PAR-PAFTA" T 6.0 ((118494.8 -127232.3) (120994.8 -127232.3) (120994.8 -126552.3) (118494.8 -126552.3)))
   ("T" "CLD-P2-PAR-YAZI" 118524.8 -126615.5 18.0 0 "\\U+0130\\U+015E\\U+0130N ADI")
   ("T" "CLD-P2-PAR-YAZI" 119114.8 -126615.5 20.0 0 "PARATONER (YILDIRIMDAN KORUNMA) PROJES\\U+0130")
   ("L" "CLD-P2-PAR-PAFTA" 118494.8 -126649.5 120994.8 -126649.5)
   ("T" "CLD-P2-PAR-YAZI" 118524.8 -126712.6 18.0 0 "YAPI SAH\\U+0130B\\U+0130")
   ("T" "CLD-P2-PAR-YAZI" 119114.8 -126712.6 20.0 0 "BROSCO \\U+0130THALAT \\U+0130HRACAT VE T\\U+0130CARET ANON\\U+0130M \\U+015E\\U+0130RKET\\U+0130")
   ("L" "CLD-P2-PAR-PAFTA" 118494.8 -126746.6 120994.8 -126746.6)
   ("T" "CLD-P2-PAR-YAZI" 118524.8 -126809.8 18.0 0 "ADRES")
   ("T" "CLD-P2-PAR-YAZI" 119114.8 -126809.8 20.0 0 "YUKARI MAHALLE / KEMALPA\\U+015EA / \\U+0130ZM\\U+0130R  -  Ada: ......  Parsel: 2")
   ("L" "CLD-P2-PAR-PAFTA" 118494.8 -126843.8 120994.8 -126843.8)
   ("T" "CLD-P2-PAR-YAZI" 118524.8 -126906.9 18.0 0 "PAFTA ADI")
   ("T" "CLD-P2-PAR-YAZI" 119114.8 -126906.9 20.0 0 "\\U+0130N\\U+0130\\U+015E \\U+0130LETKENLER\\U+0130 VE \\U+00D6L\\U+00C7\\U+00DC KLEMENSLER\\U+0130 - ZEM\\U+0130N KAT PLANI")
   ("L" "CLD-P2-PAR-PAFTA" 118494.8 -126940.9 120994.8 -126940.9)
   ("T" "CLD-P2-PAR-YAZI" 118524.8 -127004.1 18.0 0 "\\U+00D6L\\U+00C7EK / TAR\\U+0130H / PAFTA NO")
   ("T" "CLD-P2-PAR-YAZI" 119114.8 -127004.1 20.0 0 "1/100   |   19.10.2026   |   03-02")
   ("L" "CLD-P2-PAR-PAFTA" 118494.8 -127038.1 120994.8 -127038.1)
   ("T" "CLD-P2-PAR-YAZI" 118524.8 -127101.2 18.0 0 "PROJE M\\U+00DCELL\\U+0130F\\U+0130")
   ("T" "CLD-P2-PAR-YAZI" 119114.8 -127101.2 20.0 0 "Elektrik M\\U+00FChendisi - Ad\\U+0131 Soyad\\U+0131: ..............................")
   ("L" "CLD-P2-PAR-PAFTA" 118494.8 -127135.2 120994.8 -127135.2)
   ("T" "CLD-P2-PAR-YAZI" 118524.8 -127198.3 18.0 0 "ODA S\\U+0130C\\U+0130L / SMM NO")
   ("T" "CLD-P2-PAR-YAZI" 119114.8 -127198.3 20.0 0 "EMO Sicil No: ............   SMM Belge No: ............   \\U+0130mza: ............")
   ("L" "CLD-P2-PAR-PAFTA" 119084.8 -127232.3 119084.8 -126552.3)
   ("T" "CLD-P2-PAR-YAZI" 109659.0 -126692.3 70.0 0 "\\U+0130N\\U+0130\\U+015E \\U+0130LETKENLER\\U+0130 VE \\U+00D6L\\U+00C7\\U+00DC KLEMENSLER\\U+0130")
   ("T" "CLD-P2-PAR-YAZI" 109659.0 -126832.3 40.0 0 "ZEM\\U+0130N KAT PLANI  -  \\U+00D6: 1/100")
   ("T" "CLD-P2-PAR-YAZI" 109659.0 -126932.3 30.0 0 "Parsel 2  |  BROSCO \\U+0130THALAT \\U+0130HRACAT VE T\\U+0130CARET ANON\\U+0130M \\U+015E\\U+0130RKET\\U+0130")
   ("T" "CLD-P2-PAR-YAZI" 109659.0 -127012.3 26.0 0 "CLD - 19.10.2026 - mimari altl\\U+0131k: BROSCO 2 NOLU PARSEL M\\U+0130MAR\\U+0130.dwg")
   ("I" "CLD-P2-PAR-KLEMENS" "CLD_S_PAR_KLEMENS" 110762.1 -119563.1 0.0 2.5)
   ("I" "CLD-P2-PAR-INIS" "CLD_S_PAR_INIS" 110747.2 -119505.0 0.0 2.5)
   ("T" "CLD-P2-PAR-YAZI" 110732.4 -119446.8 18.0 0 "\\U+01301")
   ("I" "CLD-P2-PAR-KLEMENS" "CLD_S_PAR_KLEMENS" 111625.0 -119343.0 0.0 2.5)
   ("I" "CLD-P2-PAR-INIS" "CLD_S_PAR_INIS" 111610.2 -119284.9 0.0 2.5)
   ("T" "CLD-P2-PAR-YAZI" 111595.4 -119226.8 18.0 0 "\\U+01302")
   ("I" "CLD-P2-PAR-KLEMENS" "CLD_S_PAR_KLEMENS" 112488.0 -119123.0 0.0 2.5)
   ("I" "CLD-P2-PAR-INIS" "CLD_S_PAR_INIS" 112473.2 -119064.9 0.0 2.5)
   ("T" "CLD-P2-PAR-YAZI" 112458.3 -119006.7 18.0 0 "\\U+01303")
   ("I" "CLD-P2-PAR-KLEMENS" "CLD_S_PAR_KLEMENS" 113351.0 -118902.9 0.0 2.5)
   ("I" "CLD-P2-PAR-INIS" "CLD_S_PAR_INIS" 113336.1 -118844.8 0.0 2.5)
   ("T" "CLD-P2-PAR-YAZI" 113321.3 -118786.7 18.0 0 "\\U+01304")
   ("I" "CLD-P2-PAR-KLEMENS" "CLD_S_PAR_KLEMENS" 114213.9 -118682.9 0.0 2.5)
   ("I" "CLD-P2-PAR-INIS" "CLD_S_PAR_INIS" 114199.1 -118624.7 0.0 2.5)
   ("T" "CLD-P2-PAR-YAZI" 114184.3 -118566.6 18.0 0 "\\U+01305")
   ("I" "CLD-P2-PAR-KLEMENS" "CLD_S_PAR_KLEMENS" 115076.9 -118462.8 0.0 2.5)
   ("I" "CLD-P2-PAR-INIS" "CLD_S_PAR_INIS" 115062.1 -118404.7 0.0 2.5)
   ("T" "CLD-P2-PAR-YAZI" 115047.3 -118346.5 18.0 0 "\\U+01306")
   ("I" "CLD-P2-PAR-KLEMENS" "CLD_S_PAR_KLEMENS" 115904.9 -118300.4 0.0 2.5)
   ("I" "CLD-P2-PAR-INIS" "CLD_S_PAR_INIS" 115893.9 -118241.4 0.0 2.5)
   ("T" "CLD-P2-PAR-YAZI" 115882.9 -118182.4 18.0 0 "\\U+01307")
   ("I" "CLD-P2-PAR-KLEMENS" "CLD_S_PAR_KLEMENS" 116827.6 -118127.8 0.0 2.5)
   ("I" "CLD-P2-PAR-INIS" "CLD_S_PAR_INIS" 116816.6 -118068.8 0.0 2.5)
   ("T" "CLD-P2-PAR-YAZI" 116805.6 -118009.9 18.0 0 "\\U+01308")
   ("I" "CLD-P2-PAR-KLEMENS" "CLD_S_PAR_KLEMENS" 117703.1 -117964.3 0.0 2.5)
   ("I" "CLD-P2-PAR-INIS" "CLD_S_PAR_INIS" 117692.1 -117905.3 0.0 2.5)
   ("T" "CLD-P2-PAR-YAZI" 117681.0 -117846.4 18.0 0 "\\U+01309")
   ("I" "CLD-P2-PAR-KLEMENS" "CLD_S_PAR_KLEMENS" 118603.2 -117807.3 0.0 2.5)
   ("I" "CLD-P2-PAR-INIS" "CLD_S_PAR_INIS" 118641.5 -117761.1 0.0 2.5)
   ("T" "CLD-P2-PAR-YAZI" 118679.9 -117714.9 18.0 0 "\\U+013010")
   ("I" "CLD-P2-PAR-KLEMENS" "CLD_S_PAR_KLEMENS" 118614.0 -118812.8 0.0 2.5)
   ("I" "CLD-P2-PAR-INIS" "CLD_S_PAR_INIS" 118674.0 -118812.8 0.0 2.5)
   ("T" "CLD-P2-PAR-YAZI" 118734.0 -118812.8 18.0 0 "\\U+013011")
   ("I" "CLD-P2-PAR-KLEMENS" "CLD_S_PAR_KLEMENS" 118613.9 -119795.2 0.0 2.5)
   ("I" "CLD-P2-PAR-INIS" "CLD_S_PAR_INIS" 118673.9 -119795.2 0.0 2.5)
   ("T" "CLD-P2-PAR-YAZI" 118733.9 -119795.2 18.0 0 "\\U+013012")
   ("I" "CLD-P2-PAR-KLEMENS" "CLD_S_PAR_KLEMENS" 118613.9 -120777.7 0.0 2.5)
   ("I" "CLD-P2-PAR-INIS" "CLD_S_PAR_INIS" 118673.9 -120777.7 0.0 2.5)
   ("T" "CLD-P2-PAR-YAZI" 118733.9 -120777.7 18.0 0 "\\U+013013")
   ("I" "CLD-P2-PAR-KLEMENS" "CLD_S_PAR_KLEMENS" 118613.8 -121760.1 0.0 2.5)
   ("I" "CLD-P2-PAR-INIS" "CLD_S_PAR_INIS" 118673.8 -121760.1 0.0 2.5)
   ("T" "CLD-P2-PAR-YAZI" 118733.8 -121760.1 18.0 0 "\\U+013014")
   ("I" "CLD-P2-PAR-KLEMENS" "CLD_S_PAR_KLEMENS" 118613.8 -122742.6 0.0 2.5)
   ("I" "CLD-P2-PAR-INIS" "CLD_S_PAR_INIS" 118673.8 -122742.6 0.0 2.5)
   ("T" "CLD-P2-PAR-YAZI" 118733.8 -122742.6 18.0 0 "\\U+013015")
   ("I" "CLD-P2-PAR-KLEMENS" "CLD_S_PAR_KLEMENS" 118613.7 -123725.0 0.0 2.5)
   ("I" "CLD-P2-PAR-INIS" "CLD_S_PAR_INIS" 118673.7 -123725.0 0.0 2.5)
   ("T" "CLD-P2-PAR-YAZI" 118733.7 -123725.0 18.0 0 "\\U+013016")
   ("I" "CLD-P2-PAR-KLEMENS" "CLD_S_PAR_KLEMENS" 118592.8 -124736.0 0.0 2.5)
   ("I" "CLD-P2-PAR-INIS" "CLD_S_PAR_INIS" 118611.1 -124793.2 0.0 2.5)
   ("T" "CLD-P2-PAR-YAZI" 118629.4 -124850.3 18.0 0 "\\U+013017")))))
(defun cld:ops-p2_paratoner-3 () (cld:play (quote (
   ("I" "CLD-P2-PAR-KLEMENS" "CLD_S_PAR_KLEMENS" 118056.7 -124021.4 0.0 2.5)
   ("I" "CLD-P2-PAR-INIS" "CLD_S_PAR_INIS" 118007.9 -124056.2 0.0 2.5)
   ("T" "CLD-P2-PAR-YAZI" 117959.1 -124091.1 18.0 0 "\\U+013018")
   ("I" "CLD-P2-PAR-KLEMENS" "CLD_S_PAR_KLEMENS" 117554.2 -123317.8 0.0 2.5)
   ("I" "CLD-P2-PAR-INIS" "CLD_S_PAR_INIS" 117505.4 -123352.7 0.0 2.5)
   ("T" "CLD-P2-PAR-YAZI" 117456.6 -123387.6 18.0 0 "\\U+013019")
   ("I" "CLD-P2-PAR-KLEMENS" "CLD_S_PAR_KLEMENS" 117051.7 -122614.3 0.0 2.5)
   ("I" "CLD-P2-PAR-INIS" "CLD_S_PAR_INIS" 117002.9 -122649.2 0.0 2.5)
   ("T" "CLD-P2-PAR-YAZI" 116954.0 -122684.0 18.0 0 "\\U+013020")
   ("I" "CLD-P2-PAR-KLEMENS" "CLD_S_PAR_KLEMENS" 116549.2 -121910.8 0.0 2.5)
   ("I" "CLD-P2-PAR-INIS" "CLD_S_PAR_INIS" 116500.4 -121945.6 0.0 2.5)
   ("T" "CLD-P2-PAR-YAZI" 116451.5 -121980.5 18.0 0 "\\U+013021")
   ("I" "CLD-P2-PAR-KLEMENS" "CLD_S_PAR_KLEMENS" 116029.9 -121235.7 0.0 2.5)
   ("I" "CLD-P2-PAR-INIS" "CLD_S_PAR_INIS" 115996.5 -121285.6 0.0 2.5)
   ("T" "CLD-P2-PAR-YAZI" 115963.1 -121335.4 18.0 0 "\\U+013022")
   ("I" "CLD-P2-PAR-KLEMENS" "CLD_S_PAR_KLEMENS" 115099.5 -120986.7 0.0 2.5)
   ("I" "CLD-P2-PAR-INIS" "CLD_S_PAR_INIS" 115085.8 -121045.1 0.0 2.5)
   ("T" "CLD-P2-PAR-YAZI" 115072.1 -121103.5 18.0 0 "\\U+013023")
   ("I" "CLD-P2-PAR-KLEMENS" "CLD_S_PAR_KLEMENS" 114149.0 -120763.9 0.0 2.5)
   ("I" "CLD-P2-PAR-INIS" "CLD_S_PAR_INIS" 114135.3 -120822.4 0.0 2.5)
   ("T" "CLD-P2-PAR-YAZI" 114121.6 -120880.8 18.0 0 "\\U+013024")
   ("I" "CLD-P2-PAR-KLEMENS" "CLD_S_PAR_KLEMENS" 113198.5 -120541.2 0.0 2.5)
   ("I" "CLD-P2-PAR-INIS" "CLD_S_PAR_INIS" 113184.8 -120599.6 0.0 2.5)
   ("T" "CLD-P2-PAR-YAZI" 113171.1 -120658.0 18.0 0 "\\U+013025")
   ("I" "CLD-P2-PAR-KLEMENS" "CLD_S_PAR_KLEMENS" 112248.0 -120318.4 0.0 2.5)
   ("I" "CLD-P2-PAR-INIS" "CLD_S_PAR_INIS" 112234.3 -120376.9 0.0 2.5)
   ("T" "CLD-P2-PAR-YAZI" 112220.6 -120435.3 18.0 0 "\\U+013026")
   ("I" "CLD-P2-PAR-KLEMENS" "CLD_S_PAR_KLEMENS" 111293.7 -120094.5 0.0 2.5)
   ("I" "CLD-P2-PAR-INIS" "CLD_S_PAR_INIS" 111272.2 -120150.5 0.0 2.5)
   ("T" "CLD-P2-PAR-YAZI" 111250.7 -120206.5 18.0 0 "\\U+013027")
   ("T" "CLD-P2-PAR-TABLO" 122094.8 -116555.9 32.5 0 "LEJANT")
   ("P" "CLD-P2-PAR-TABLO" T 0.0 ((122094.8 -116580.9) (123411.8 -116580.9) (123411.8 -116925.9) (122094.8 -116925.9)))
   ("P" "CLD-P2-PAR-YAKALAMA" nil 0.0 ((122119.8 -116633.4) (122369.8 -116633.4)))
   ("T" "CLD-P2-PAR-TABLO" 122394.8 -116633.4 25.0 7 "Yakalama iletkeni \\U+00D88 mm Al/galvaniz, klips aral\\U+0131\\U+011F\\U+0131 1 m")
   ("I" "CLD-P2-PAR-TABLO" "CLD_S_PAR_UC" 122244.8 -116713.4 0.0 1.625)
   ("T" "CLD-P2-PAR-TABLO" 122394.8 -116713.4 25.0 7 "Yakalama \\U+00E7ubu\\U+011Fu: k\\U+00F6\\U+015Fe / mahya h=1,0 m, \\U+00E7at\\U+0131 fan\\U+0131 yan\\U+0131nda h=1,5 m")
   ("I" "CLD-P2-PAR-TABLO" "CLD_S_PAR_INIS" 122244.8 -116793.4 0.0 1.182)
   ("T" "CLD-P2-PAR-TABLO" 122394.8 -116793.4 25.0 7 "\\U+0130ni\\U+015F iletkeni \\U+00D88 mm (veya s\\U+00FCreklili\\U+011Fi sa\\U+011Flanm\\U+0131\\U+015F \\U+00E7elik kolon)")
   ("I" "CLD-P2-PAR-TABLO" "CLD_S_PAR_KLEMENS" 122244.8 -116873.4 0.0 2.167)
   ("T" "CLD-P2-PAR-TABLO" 122394.8 -116873.4 25.0 7 "\\U+00D6l\\U+00E7\\U+00FC (ay\\U+0131rma) klemensi h=0,5 m, temel topraklamas\\U+0131na ba\\U+011Fl\\U+0131")
   ("TB" "CLD-P2-PAR-TABLO" 123811.8 -116555.9 25.0 "YILDIRIM R\\U+0130SK DE\\U+011EERLEND\\U+0130RMES\\U+0130 (verim y\\U+00F6ntemi, IEC 61024-1-1 / TS EN 62305 seviyeleri)" (("B\\U+00DCY\\U+00DCKL\\U+00DCK" "DE\\U+011EER" "A\\U+00C7IKLAMA") ("Taban alan\\U+0131 / \\U+00E7evre / y\\U+00FCkseklik" "2.090 m\\U+00B2 / 248,2 m / 11,21 m" "Mimari plan ve kesit") ("E\\U+015Fde\\U+011Fer toplama alan\\U+0131 Ad" "13.969 m\\U+00B2" "Taban konturu 3H kadar geni\\U+015Fletilerek") ("Y\\U+0131ld\\U+0131r\\U+0131m d\\U+00FC\\U+015Fme yo\\U+011Funlu\\U+011Fu Ng" "3,0 /km\\U+00B2/y\\U+0131l" "\\U+0130zmir b\\U+00F6lgesi (~30 g\\U+00F6k g\\U+00FCr\\U+00FClt\\U+00FCl\\U+00FC g\\U+00FCn)") ("Konum katsay\\U+0131s\\U+0131 Cd" "0,5" "OSB i\\U+00E7inde benzer y\\U+00FCkseklikte yap\\U+0131larla \\U+00E7evrili") ("Beklenen y\\U+0131ll\\U+0131k d\\U+00FC\\U+015Fme Nd" "0,0210" "Nd = Ng \\U+00B7 Ad \\U+00B7 Cd \\U+00B7 10^-6") ("Kabul edilebilir s\\U+0131kl\\U+0131k Nc" "0,0010" "Sanayi yap\\U+0131s\\U+0131") ("Gerekli verim E = 1 - Nc/Nd" "0,952" "Se\\U+00E7im: E \\U+2264 0,80 IV, \\U+2264 0,90 III, \\U+2264 0,95 II, \\U+2264 0,98 I") ("Koruma seviyesi" "LPL I" "Sistem verimi 0,98") ("Yuvarlanan k\\U+00FCre yar\\U+0131\\U+00E7ap\\U+0131" "20 m" "") ("A\\U+011F (g\\U+00F6z) boyutu" "5 x 5 m" "") ("\\U+0130ni\\U+015F iletkeni aral\\U+0131\\U+011F\\U+0131 / adedi" "\\U+2264 10 m / 27 adet" "en b\\U+00FCy\\U+00FCk aral\\U+0131k 9,8 m, t\\U+00FCm k\\U+00F6\\U+015Felerde ini\\U+015F") ("kc = 1/(2n) + 0,1 + 0,2\\U+00B7(c/h)^(1/3)" "0,31" "TS EN 62305-3 Ek C") ("Ay\\U+0131rma mesafesi s = ki\\U+00B7kc/km\\U+00B7l" "0,28 m (l=H)" "\\U+00E7at\\U+0131 cihazlar\\U+0131: 0,48 m (l=19,5 m), ki=0,08, km=1")))
   ("TB" "CLD-P2-PAR-TABLO" 123811.8 -117630.9 25.0 "MALZEME \\U+00D6ZET\\U+0130" (("MALZEME" "M\\U+0130KTAR") ("Yakalama iletkeni \\U+00D88 mm (\\U+00E7evre + a\\U+011F)" "1.143 m") ("\\U+0130ni\\U+015F iletkeni \\U+00D88 mm" "303 m (27 adet)") ("Yakalama \\U+00E7ubu\\U+011Fu h=1,0 m (k\\U+00F6\\U+015Fe / mahya)" "27 adet") ("Yakalama \\U+00E7ubu\\U+011Fu h=1,5 m (\\U+00E7at\\U+0131 fan\\U+0131 yan\\U+0131nda, a\\U+011Fa ba\\U+011Fl\\U+0131)" "12 adet") ("\\U+0130letken tutucu klips (1 m aral\\U+0131k)" "1.446 adet") ("\\U+00D6l\\U+00E7\\U+00FC (ay\\U+0131rma) klemensi - \\U+00F6l\\U+00E7\\U+00FC kutusu TOPRAKLAMA paftas\\U+0131nda" "27 adet")))
   ("NT" "CLD-P2-PAR-TABLO" 123811.8 -118355.9 25.0 "NOTLAR" ("1- Koruma seviyesi verim y\\U+00F6ntemiyle (IEC 61024-1-1) belirlenmi\\U+015F; tesisat TS EN 62305-3/4 e g\\U+00F6re Faraday a\\U+011F\\U+0131 y\\U+00F6ntemiyle tasarlanm\\U+0131\\U+015Ft\\U+0131r." "2- Metal \\U+00E7at\\U+0131 paneli kal\\U+0131nl\\U+0131\\U+011F\\U+0131 \\U+2265 0,5 mm ise do\\U+011Fal yakalama ucu olarak kullan\\U+0131labilir (delinme kabul edilirse)." "3- \\U+00C7elik kolonlar\\U+0131n ankrajlar\\U+0131 temel topraklamas\\U+0131na ba\\U+011Fl\\U+0131 oldu\\U+011Fundan do\\U+011Fal ini\\U+015F iletkeni olarak kullan\\U+0131labilir." "4- \\U+00C7at\\U+0131 fanlar\\U+0131 yanlar\\U+0131ndaki h=1,5 m yakalama \\U+00E7ubuklar\\U+0131 ile korunur; a\\U+011F iletkenleri fanlar\\U+0131n \\U+00E7evresinden en az s mesafesiyle dola\\U+015Ft\\U+0131r\\U+0131lm\\U+0131\\U+015Ft\\U+0131r." "5- T\\U+00FCm ba\\U+011Flant\\U+0131lar TS EN 62561 belgeli klemenslerle yap\\U+0131lacak, \\U+00F6l\\U+00E7\\U+00FC klemensleri \\U+00F6l\\U+00E7\\U+00FC kutusu i\\U+00E7inde olacakt\\U+0131r." "6- Gelen enerji/ileti\\U+015Fim hatlar\\U+0131na ADP de Tip 1+2 parafudr (SPD) konulacakt\\U+0131r (TS EN 62305-4)."))
   ("P" "CLD-P2-PAR-PAFTA" T 10.0 ((121894.8 -119990.9) (127294.8 -119990.9) (127294.8 -116255.9) (121894.8 -116255.9)))
   ("P" "CLD-P2-PAR-PAFTA" nil 6.0 ((121894.8 -119240.9) (127294.8 -119240.9)))
   ("T" "CLD-P2-PAR-YAZI" 121994.8 -119430.9 70.0 0 "HESAP TABLOLARI, CETVELLER VE NOTLAR")
   ("T" "CLD-P2-PAR-YAZI" 121994.8 -119590.9 40.0 0 "PARATONER (YILDIRIMDAN KORUNMA) PROJES\\U+0130  -  \\U+00D6l\\U+00E7eksiz")
   ("P" "CLD-P2-PAR-PAFTA" T 6.0 ((124794.8 -119970.9) (127294.8 -119970.9) (127294.8 -119260.9) (124794.8 -119260.9)))
   ("T" "CLD-P2-PAR-YAZI" 124824.8 -119326.8 18.0 0 "\\U+0130\\U+015E\\U+0130N ADI")
   ("T" "CLD-P2-PAR-YAZI" 125414.8 -119326.8 20.0 0 "PARATONER (YILDIRIMDAN KORUNMA) PROJES\\U+0130")
   ("L" "CLD-P2-PAR-PAFTA" 124794.8 -119362.3 127294.8 -119362.3)
   ("T" "CLD-P2-PAR-YAZI" 124824.8 -119428.2 18.0 0 "YAPI SAH\\U+0130B\\U+0130")
   ("T" "CLD-P2-PAR-YAZI" 125414.8 -119428.2 20.0 0 "BROSCO \\U+0130THALAT \\U+0130HRACAT VE T\\U+0130CARET ANON\\U+0130M \\U+015E\\U+0130RKET\\U+0130")
   ("L" "CLD-P2-PAR-PAFTA" 124794.8 -119463.7 127294.8 -119463.7)
   ("T" "CLD-P2-PAR-YAZI" 124824.8 -119529.6 18.0 0 "ADRES")
   ("T" "CLD-P2-PAR-YAZI" 125414.8 -119529.6 20.0 0 "YUKARI MAHALLE / KEMALPA\\U+015EA / \\U+0130ZM\\U+0130R  -  Ada: ......  Parsel: 2")
   ("L" "CLD-P2-PAR-PAFTA" 124794.8 -119565.1 127294.8 -119565.1)
   ("T" "CLD-P2-PAR-YAZI" 124824.8 -119631.1 18.0 0 "PAFTA ADI")
   ("T" "CLD-P2-PAR-YAZI" 125414.8 -119631.1 20.0 0 "HESAP TABLOLARI VE NOTLAR")
   ("L" "CLD-P2-PAR-PAFTA" 124794.8 -119666.6 127294.8 -119666.6)
   ("T" "CLD-P2-PAR-YAZI" 124824.8 -119732.5 18.0 0 "\\U+00D6L\\U+00C7EK / TAR\\U+0130H / PAFTA NO")
   ("T" "CLD-P2-PAR-YAZI" 125414.8 -119732.5 20.0 0 "\\U+00D6l\\U+00E7eksiz   |   19.10.2026   |   03-03")
   ("L" "CLD-P2-PAR-PAFTA" 124794.8 -119768.0 127294.8 -119768.0)
   ("T" "CLD-P2-PAR-YAZI" 124824.8 -119833.9 18.0 0 "PROJE M\\U+00DCELL\\U+0130F\\U+0130")
   ("T" "CLD-P2-PAR-YAZI" 125414.8 -119833.9 20.0 0 "Elektrik M\\U+00FChendisi - Ad\\U+0131 Soyad\\U+0131: ..............................")
   ("L" "CLD-P2-PAR-PAFTA" 124794.8 -119869.4 127294.8 -119869.4)
   ("T" "CLD-P2-PAR-YAZI" 124824.8 -119935.4 18.0 0 "ODA S\\U+0130C\\U+0130L / SMM NO")
   ("T" "CLD-P2-PAR-YAZI" 125414.8 -119935.4 20.0 0 "EMO Sicil No: ............   SMM Belge No: ............   \\U+0130mza: ............")
   ("L" "CLD-P2-PAR-PAFTA" 125384.8 -119970.9 125384.8 -119260.9)))))

(defun c:CLD_P2_PARATONER ( / *error* olderr)
  (setq *error* cld:err)
  (setq *cld-u* 100.0 *cld-ext* (list 0.0 0.0 1.0))
  (cld:begin "CLD-P2-PAR-*")
  (cld:unlock "CLD-P2-PAR-*")
  (cld:unlock "CLD-PAR-*")
  (cld:clear "CLD-PAR-*")
  (cld:ops-p2_paratoner-layers)
  (cld:clear "CLD-P2-PAR-*")
  (cld:def-symbols)
  (cld:ops-p2_paratoner-1)
  (cld:ops-p2_paratoner-2)
  (cld:ops-p2_paratoner-3)
  (cld:end "CLD: Parsel 2 - PARATONER (YILDIRIMDAN KORUNMA) PROJESI cizildi")
  (princ))

(if (cld:wrong-dwg "2" (list "3" "4" "5"))
  (princ "\nCLD UYARI: Bu dosya PARSEL 2 icindir; acik cizim baska bir parsele ait gorunuyor. Yine de cizmek icin CLD_P2_PARATONER yazin.")
  (progn (princ "\nCLD: Parsel 2 PARATONER yukleniyor, cizim olusturuluyor...") (c:CLD_P2_PARATONER)))
(princ "\nCLD: Yeniden cizmek icin komut: CLD_P2_PARATONER")
(princ)
