;;; ==========================================================================
;;; CLD_P2_04_KUVVETLI_AKIM.lsp
;;; PARSEL 2 - KUVVETLI AKIM - GUC DAGITIM PROJESI
;;; Isveren : BROSCO ITHALAT IHRACAT VE TICARET ANONIM SIRKETI
;;; Konum   : YUKARI MAHALLE / KEMALPASA / IZMIR
;;; Kaynak  : BROSCO 2 NOLU PARSEL MIMARI.dwg (mimari paftalar)
;;; Kullanim: APPLOAD ile yukleyin -> cizim otomatik olusur.
;;;          Yeniden cizmek icin komut: CLD_P2_KUVVETLIAKIM
;;;          Tum ciktilar "CLD-P2-KAK-*" katmanlarindadir; yeniden calistirmada bu katmanlar temizlenir.
;;;          Guvenlik uyarisi gelirse "Bir kez yukle" deyin veya klasoru Secenekler > Dosyalar >
;;;          Guvenilen Konumlar (TRUSTEDPATHS) listesine ekleyin.
;;; Uretici : CLD (Claude) otomatik muhendislik motoru - tum isimler CLD onekli.
;;;   Mimari: 2 kat, 12 mahal, kat kotlari ZK=+0.00, 1K=+3.00, bina yuksekligi 11.21 m
;;;   Elektrik: kurulu 238.6 kW, talep 148.5 kW, trafo 250 kVA, KMP 90 kVAr, jenerator 45 kVA
;;;   Aydinlatma: 107 armatur, 29 priz/cikis, 46 linye, 8 pano
;;;   Topraklama: R=0.97 ohm (birlesik), paratoner LPL I, 27 inis
;;;   Mekanik: VRF 4.4 kW ic unite, dis unite 5.0 kW
;;;   Sihhi: 12 armatur, 1 pis su kolonu, 14 yagmur inisi
;;; ==========================================================================

;;; ==========================================================================
;;; CLD CORE  -  ortak cizim altyapisi (katman, stil, varlik, tablo, oynatici)
;;; Tum isimler CLD onekli. ActiveX (vla-) kullanilmaz: AutoCAD / BricsCAD /
;;; accoreconsole uyumlu saf AutoLISP + entmake.
;;; Mimari paftalar WCS XZ duzleminde (ekstruzyon 0,-1,0) cizildiginden tum
;;; varliklar ayni duzlemde (*cld-ext*) uretilir; koordinatlar pafta (OCS)
;;; koordinatidir.
;;; ==========================================================================

(setq *cld-ver* "1.0")
(if (not *cld-ext*) (setq *cld-ext* '(0.0 0.0 1.0)))
(if (not *cld-u*) (setq *cld-u* 100.0))

;;; ---------------------------------------------------------------- yardimci
(defun cld:m (x) (* x *cld-u*))
(defun cld:3d (p) (list (float (car p)) (float (cadr p)) 0.0))
(defun cld:2d (p) (list (float (car p)) (float (cadr p))))
(defun cld:pxy (p dx dy) (list (+ (car p) dx) (+ (cadr p) dy)))
(defun cld:wcs (p) (trans (cld:3d p) *cld-ext* 0))
(defun cld:top (lay) (/= lay "0"))
(defun cld:x210 (lay) (if (cld:top lay) (list (cons 210 *cld-ext*) '(410 . "Model")) '()))
;; renk / cizgi tipi / kalinlik her zaman acik yazilir: cizimdeki CECOLOR / CELTYPE / CELWEIGHT ne olursa olsun
;; katmandan (ByLayer) gelir; blok icindekiler ByBlock
(defun cld:col (lay)
  (if (= lay "0") '((62 . 0) (6 . "ByBlock") (370 . -2)) '((62 . 256) (6 . "ByLayer") (370 . -1))))
(defun cld:dlen (s / n i)
  ;; gorunen karakter sayisi (\U+XXXX = 1 karakter)
  (setq n 0 i 1)
  (while (<= i (strlen s))
    (if (and (= (substr s i 3) "\\U+") (<= (+ i 6) (strlen s))) (setq i (+ i 7)) (setq i (1+ i)))
    (setq n (1+ n)))
  n)
(defun cld:maxl (l) (if l (apply 'max l) 0))
(defun cld:sum (l) (apply '+ (cons 0 l)))
(defun cld:nth-or (i l def) (if (and l (< i (length l))) (nth i l) def))
(defun cld:range (n / i r) (setq i (1- n)) (while (>= i 0) (setq r (cons i r) i (1- i))) r)

;;; ------------------------------------------------------ tablo kayitlari
(defun cld:ltype (nm desc dash gap / sc)
  (if (not (tblsearch "LTYPE" nm))
    (progn
      (setq sc (max 1e-6 (getvar "LTSCALE")))
      (entmake (list '(0 . "LTYPE") '(100 . "AcDbSymbolTableRecord") '(100 . "AcDbLinetypeTableRecord")
                     (cons 2 nm) '(70 . 0) (cons 3 desc) '(72 . 65) '(73 . 2)
                     (cons 40 (/ (+ dash gap) sc)) (cons 49 (/ dash sc)) '(74 . 0) (cons 49 (- (/ gap sc))) '(74 . 0)))))
  nm)
(defun cld:style ()
  (if (not (tblsearch "STYLE" "CLD_YAZI"))
    (entmake '((0 . "STYLE") (100 . "AcDbSymbolTableRecord") (100 . "AcDbTextStyleTableRecord")
               (2 . "CLD_YAZI") (70 . 0) (40 . 0.0) (41 . 0.85) (50 . 0.0) (71 . 0) (42 . 2.5)
               (3 . "arial.ttf") (4 . ""))))
  "CLD_YAZI")
(defun cld:lay (nm col lt lw / e ed)
  (if (not (tblsearch "LAYER" nm))
    (entmake (list '(0 . "LAYER") '(100 . "AcDbSymbolTableRecord") '(100 . "AcDbLayerTableRecord")
                   (cons 2 nm) '(70 . 0) (cons 62 col)
                   (cons 6 (if (and lt (tblsearch "LTYPE" lt)) lt "Continuous"))
                   (cons 370 lw)))
    (progn
      (setq e (tblobjname "LAYER" nm) ed (entget e))
      (setq ed (subst (cons 70 0) (assoc 70 ed) ed))
      (setq ed (subst (cons 62 col) (assoc 62 ed) ed))
      (if (and lt (tblsearch "LTYPE" lt) (assoc 6 ed)) (setq ed (subst (cons 6 lt) (assoc 6 ed) ed)))
      (if (assoc 370 ed) (setq ed (subst (cons 370 lw) (assoc 370 ed) ed)))
      (entmod ed)))
  nm)

;;; ---------------------------------------------------- varlik olusturucular
;;; lay "0" = blok tanimi icerigi (BYBLOCK renk, blok koordinati)
(defun cld:e-line (a b lay)
  (append (list '(0 . "LINE") (cons 8 lay)) (cld:col lay)
          (if (cld:top lay) (list (cons 10 (cld:wcs a)) (cons 11 (cld:wcs b))) (list (cons 10 (cld:3d a)) (cons 11 (cld:3d b))))
          (cld:x210 lay)))
(defun cld:e-circle (c r lay)
  (append (list '(0 . "CIRCLE") (cons 8 lay)) (cld:col lay) (list (cons 10 (cld:3d c)) (cons 40 r)) (cld:x210 lay)))
(defun cld:e-arc (c r a1 a2 lay)
  (append (list '(0 . "ARC") (cons 8 lay)) (cld:col lay) (list (cons 10 (cld:3d c)) (cons 40 r) (cons 50 a1) (cons 51 a2)) (cld:x210 lay)))
(defun cld:e-pl (pts closed w lay)
  (append (list '(0 . "LWPOLYLINE") '(100 . "AcDbEntity") (cons 8 lay)) (cld:col lay)
          (list '(100 . "AcDbPolyline") (cons 90 (length pts)) (cons 70 (+ (if closed 1 0) (if (cld:top lay) 128 0))) (cons 43 w) '(38 . 0.0))
          (mapcar '(lambda (p) (cons 10 (cld:2d p))) pts)
          (cld:x210 lay)))
(defun cld:e-dot (c r lay)
  (append (list '(0 . "LWPOLYLINE") '(100 . "AcDbEntity") (cons 8 lay)) (cld:col lay)
          (list '(100 . "AcDbPolyline") '(90 . 2) '(70 . 1) (cons 43 r) '(38 . 0.0)
                (cons 10 (list (- (car c) (/ r 2.0)) (cadr c))) '(42 . 1.0)
                (cons 10 (list (+ (car c) (/ r 2.0)) (cadr c))) '(42 . 1.0))
          (cld:x210 lay)))
(defun cld:e-solid (p1 p2 p3 p4 lay)
  (append (list '(0 . "SOLID") (cons 8 lay)) (cld:col lay)
          (list (cons 10 (cld:3d p1)) (cons 11 (cld:3d p2)) (cons 12 (cld:3d p4)) (cons 13 (cld:3d p3)))
          (cld:x210 lay)))
(defun cld:e-text (p h s j lay / ed p3)
  ;; j: 0 sol-taban, 1 orta-taban, 2 sag-taban, 4 orta-orta, 7 sol-orta, 9 sag-orta
  (setq p3 (cld:3d p))
  (setq ed (append (list '(0 . "TEXT") (cons 8 lay)) (cld:col lay)
                   (list (cons 7 (cld:style)) (cons 10 p3) (cons 40 h) (cons 1 s) '(50 . 0.0) '(41 . 0.85))))
  (setq ed (cond ((= j 1) (append ed (list '(72 . 1) (cons 11 p3) '(73 . 0))))
                 ((= j 2) (append ed (list '(72 . 2) (cons 11 p3) '(73 . 0))))
                 ((= j 4) (append ed (list '(72 . 1) (cons 11 p3) '(73 . 2))))
                 ((= j 7) (append ed (list '(72 . 0) (cons 11 p3) '(73 . 2))))
                 ((= j 9) (append ed (list '(72 . 2) (cons 11 p3) '(73 . 2))))
                 (T ed)))
  (append ed (cld:x210 lay)))
(defun cld:e-ins (blk p sc rot lay)
  (append (list '(0 . "INSERT") (cons 8 lay)) (cld:col lay) (list (cons 2 blk) (cons 10 (cld:3d p))
                (cons 41 sc) (cons 42 sc) (cons 43 sc) (cons 50 rot))
          (cld:x210 lay)))
(defun cld:line (a b lay) (entmake (cld:e-line a b lay)))
(defun cld:pl (pts closed w lay) (if (cdr pts) (entmake (cld:e-pl pts closed w lay))))
(defun cld:txt (p h s j lay) (entmake (cld:e-text p h s j lay)))
(defun cld:rect (p1 p2 lay) (cld:pl (list p1 (list (car p2) (cadr p1)) p2 (list (car p1) (cadr p2))) T 0.0 lay))

;;; ------------------------------------------------------------ blok tanimi
(defun cld:defblk (name ents)
  (if (not (tblsearch "BLOCK" name))
    (progn
      (entmake (list '(0 . "BLOCK") (cons 2 name) '(70 . 0) '(10 0.0 0.0 0.0) '(8 . "0")))
      (foreach e ents (entmake e))
      (entmake '((0 . "ENDBLK") (8 . "0")))))
  name)

;;; mimari altlik blogu: plines ((kapali (x y) (x y) ...) ...)  texts ((x y h "yazi") ...)
(defun cld:defblk-bg (name plines texts)
  (if (not (tblsearch "BLOCK" name))
    (progn
      (entmake (list '(0 . "BLOCK") (cons 2 name) '(70 . 0) '(10 0.0 0.0 0.0) '(8 . "0")))
      (foreach p plines (if (cddr p) (entmake (cld:e-pl (cdr p) (car p) 0.0 "0"))))
      (foreach s texts (entmake (cld:e-text (list (car s) (cadr s)) (caddr s) (cadddr s) 4 "0")))
      (entmake '((0 . "ENDBLK") (8 . "0")))))
  name)

;;; ------------------------------------------------------------------ tablo
;;; rows: ((hucre ...) ...)  ilk satir baslik. Sutun genislikleri otomatik.
(defun cld:table (org title rows h lay / ncol widths rh y x w i r cw tw pad s)
  (setq pad (* 0.6 h) rh (* 2.0 h))
  (setq ncol (cld:maxl (mapcar 'length rows)))
  (setq widths (mapcar '(lambda (c)
                          (+ (* 2 pad) (* 0.66 h (cld:maxl (mapcar '(lambda (r) (cld:dlen (cld:nth-or c r ""))) rows)))))
                       (cld:range ncol)))
  (setq tw (cld:sum widths) x (car org) y (cadr org))
  (if (and title (/= title ""))
    (progn
      (cld:rect (list x y) (list (+ x tw) (- y (* 1.5 rh))) lay)
      (cld:txt (list (+ x pad) (- y (* 0.75 rh))) (* 1.3 h) title 7 lay)
      (setq y (- y (* 1.5 rh)))))
  (setq i 0)
  (foreach r rows
    (setq x (car org) cw 0)
    (cld:rect (list x y) (list (+ x tw) (- y rh)) lay)
    (foreach w widths
      (if (> cw 0) (cld:line (list x y) (list x (- y rh)) lay))
      (setq s (cld:nth-or cw r ""))
      (if (/= s "") (cld:txt (list (+ x pad) (- y (* 0.5 rh))) h s 7 lay))
      (setq x (+ x w) cw (1+ cw)))
    (if (= i 0) (cld:pl (list (list (car org) (- y rh)) (list (+ (car org) tw) (- y rh))) nil (* 0.12 h) lay))
    (setq y (- y rh) i (1+ i)))
  (list (- y (* 2.0 h)) tw))
(defun cld:notes (org title lines h lay / y)
  (setq y (cadr org))
  (if (and title (/= title "")) (progn (cld:txt (list (car org) y) (* 1.3 h) title 0 lay) (setq y (- y (* 2.2 h)))))
  (foreach s lines (cld:txt (list (car org) y) h s 0 lay) (setq y (- y (* 1.7 h))))
  (- y h))

;;; ------------------------------------------------------------- oynatici
;;; Hesap motorunun urettigi cizim komutlari:
;;;  ("LY" ad renk cizgitipi kalinlik)        katman
;;;  ("I" lay blok x y aci olcek)             sembol (olcek * *cld-u*)
;;;  ("L" lay x1 y1 x2 y2)                    cizgi
;;;  ("P" lay kapali genislik ((x y) ...))    polyline
;;;  ("C" lay x y r)                          daire
;;;  ("D" lay x y r)                          dolu daire
;;;  ("T" lay x y h hiza "yazi")              yazi
;;;  ("TB" lay x y h "baslik" satirlar)       tablo
;;;  ("NT" lay x y h "baslik" satirlar)       not blogu
(defun cld:op (o / k)
  (setq k (car o))
  (cond ((= k "I") (entmake (cld:e-ins (nth 2 o) (list (nth 3 o) (nth 4 o)) (* (nth 6 o) *cld-u*) (nth 5 o) (nth 1 o))))
        ((= k "L") (cld:line (list (nth 2 o) (nth 3 o)) (list (nth 4 o) (nth 5 o)) (nth 1 o)))
        ((= k "P") (cld:pl (nth 4 o) (nth 2 o) (nth 3 o) (nth 1 o)))
        ((= k "C") (entmake (cld:e-circle (list (nth 2 o) (nth 3 o)) (nth 4 o) (nth 1 o))))
        ((= k "D") (entmake (cld:e-dot (list (nth 2 o) (nth 3 o)) (nth 4 o) (nth 1 o))))
        ((= k "T") (cld:txt (list (nth 2 o) (nth 3 o)) (nth 4 o) (nth 6 o) (nth 5 o) (nth 1 o)))
        ((= k "TB") (cld:table (list (nth 2 o) (nth 3 o)) (nth 5 o) (nth 6 o) (nth 4 o) (nth 1 o)))
        ((= k "NT") (cld:notes (list (nth 2 o) (nth 3 o)) (nth 5 o) (nth 6 o) (nth 4 o) (nth 1 o)))
        ((= k "LY") (cld:lay (nth 1 o) (nth 2 o) (nth 3 o) (nth 4 o)))
        ((= k "BK") (cld:defblk-bg (nth 1 o) (nth 2 o) (nth 3 o)))))
(defun cld:play (ops / r)
  (foreach o ops
    (setq r (vl-catch-all-apply 'cld:op (list o)))
    (cond ((vl-catch-all-error-p r) (setq *cld-bad* (cons (list (car o) (nth 1 o) (vl-catch-all-error-message r)) *cld-bad*)))
          ((and (null r) (or (member (car o) '("I" "L" "C" "D" "T")) (and (= (car o) "P") (cdr (nth 4 o)))))
           (setq *cld-bad* (cons (list (car o) (nth 1 o) (if (= (car o) "I") (nth 2 o) "")) *cld-bad*)))
          (T (setq *cld-n* (1+ *cld-n*))))))

;;; ------------------------------------------------------- calisma ortami
(defun cld:clear (pat / ss i n)
  (setq n 0)
  (if (setq ss (ssget "_X" (list (cons 8 pat))))
    (progn (setq i 0) (while (< i (sslength ss)) (entdel (ssname ss i)) (setq i (1+ i) n (1+ n)))))
  n)
(defun cld:begin (pat)
  (setq *cld-old* (list (getvar "CMDECHO") (getvar "OSMODE")) *cld-n* 0 *cld-bad* nil)
  (setvar "CMDECHO" 0)
  (setvar "OSMODE" 0)
  ;; cizim model alaninda olusur (bir yerlesim sekmesi acik olsa bile)
  (if (= 0 (getvar "TILEMODE")) (vl-catch-all-apply 'setvar (list "TILEMODE" 1)))
  (vl-catch-all-apply 'command-s (list "_.UNDO" "_BEGIN"))
  (cld:style)
  (cld:ltype "CLD_KESIK" "CLD kesik __ __" (cld:m 0.30) (cld:m 0.15))
  (cld:ltype "CLD_NOKTALI" "CLD noktali . . ." (cld:m 0.05) (cld:m 0.10))
  (cld:ltype "CLD_UZUNKESIK" "CLD uzun kesik ____ ____" (cld:m 0.80) (cld:m 0.20)))
;;; disiplin katmanlarinin kilidini kaldir / coz (eski cikti silinebilsin)
(defun cld:unlock (pat / tl ed)
  (setq tl (tblnext "LAYER" T))
  (while tl
    (if (and (wcmatch (cdr (assoc 2 tl)) pat) (/= 0 (logand 5 (cdr (assoc 70 tl)))))
      (progn (setq ed (entget (tblobjname "LAYER" (cdr (assoc 2 tl)))))
             (entmod (subst (cons 70 0) (assoc 70 ed) ed))))
    (setq tl (tblnext "LAYER"))))
(defun cld:restore ()
  (vl-catch-all-apply 'command-s (list "_.UNDO" "_END"))
  (if *cld-old* (progn (setvar "CMDECHO" (car *cld-old*)) (setvar "OSMODE" (cadr *cld-old*))))
  (setq *cld-old* nil))
(defun cld:first5 (l / r i) (setq i 0) (foreach x l (if (< i 5) (setq r (cons x r))) (setq i (1+ i))) (reverse r))
(defun cld:end (msg)
  (cld:restore)
  (princ (strcat "\n" msg " (" (itoa *cld-n*) " varlik/komut)"))
  (if *cld-bad*
    (progn
      (princ (strcat "\nCLD UYARI: " (itoa (length *cld-bad*)) " varlik olusturulamadi, ilkleri:"))
      (foreach b (cld:first5 (reverse *cld-bad*)) (princ (strcat "\n   " (vl-princ-to-string b))))))
  (princ))
;;; acik cizim baska bir parsele mi ait? (dosya adinda baska parselin "<n> NOLU" ifadesi)
(defun cld:wrong-dwg (parcel others / nm bad)
  (setq nm (strcase (getvar "DWGNAME")))
  (foreach o others (if (wcmatch nm (strcat "* " o " NOLU*,BROSCO " o " *,P" o ".DWG")) (setq bad T)))
  (and bad (not (wcmatch nm (strcat "* " parcel " NOLU*,BROSCO " parcel " *,P" parcel ".DWG")))))
(defun cld:err (m)
  (cld:restore)
  (if (not (member m '("Function cancelled" "quit / exit abort"))) (princ (strcat "\nCLD HATA: " m)))
  (princ))


;;; ==========================================================================
;;; CLD SEMBOL KUTUPHANESI - bloklar 1 birim = 1 m tanimlanir, cizime
;;; (olcek x *cld-u*) ile yerlestirilir. Duvar sembollerinde duvar yerel x=0,
;;; sembol +X yonune (mahal icine) bakar.
;;; ==========================================================================

(defun cld:b-box (w h)
  (cld:e-pl (list (list (- (/ w 2)) (- (/ h 2))) (list (/ w 2) (- (/ h 2))) (list (/ w 2) (/ h 2)) (list (- (/ w 2)) (/ h 2))) T 0.0 "0"))
(defun cld:b-wallbox (d w)
  (cld:e-pl (list (list 0.0 (- (/ w 2))) (list d (- (/ w 2))) (list d (/ w 2)) (list 0.0 (/ w 2))) T 0.0 "0"))
(defun cld:b-x (r)
  (list (cld:e-line (list (- r) (- r)) (list r r) "0") (cld:e-line (list (- r) r) (list r (- r)) "0")))
(defun cld:b-txt (p h s) (cld:e-text p h s 4 "0"))

(defun cld:def-symbols ( / r)
  ;; ---------------- AYDINLATMA
  (setq r 0.12)
  (cld:defblk "CLD_S_DL" (append (list (cld:e-circle '(0 0) r "0")) (cld:b-x (* r 0.707))))
  (cld:defblk "CLD_S_DLB" (append (list (cld:e-circle '(0 0) r "0") (cld:e-circle '(0 0) (* r 1.35) "0")) (cld:b-x (* r 0.707))))
  (cld:defblk "CLD_S_HB" (append (list (cld:e-circle '(0 0) 0.30 "0") (cld:e-circle '(0 0) 0.12 "0")) (cld:b-x 0.21)))
  (cld:defblk "CLD_S_PNL" (append (list (cld:b-box 0.6 0.6)) (cld:b-x 0.3)))
  (cld:defblk "CLD_S_ETJ" (list (cld:b-box 1.2 0.2) (cld:e-line '(-0.6 0.0) '(0.6 0.0) "0")
                                (cld:e-line '(-0.5 -0.1) '(-0.5 0.1) "0") (cld:e-line '(0.5 -0.1) '(0.5 0.1) "0")))
  (cld:defblk "CLD_S_PLF" (list (cld:e-circle '(0 0) 0.15 "0") (cld:e-dot '(0 0) 0.07 "0")))
  (cld:defblk "CLD_S_ACIL" (list (cld:b-box 0.32 0.16) (cld:e-solid '(-0.16 -0.08) '(0.16 -0.08) '(0.16 0.08) '(0.16 0.08) "0")))
  (cld:defblk "CLD_S_EXIT" (list (cld:b-box 0.40 0.20) (cld:e-line '(-0.14 0) '(0.12 0) "0") (cld:e-line '(0.12 0) '(0.04 0.06) "0")
                                 (cld:e-line '(0.12 0) '(0.04 -0.06) "0")))
  (cld:defblk "CLD_S_PRJ" (list (cld:e-pl '((-0.15 -0.10) (0.15 -0.10) (0.22 0.12) (-0.22 0.12)) T 0.0 "0") (cld:e-line '(-0.15 0.0) '(0.15 0.0) "0")))
  (cld:defblk "CLD_S_BOLLARD" (list (cld:e-circle '(0 0) 0.12 "0") (cld:e-dot '(0 0) 0.12 "0")))
  ;; ---------------- PRIZ / ANAHTAR (duvar sembolleri)
  (cld:defblk "CLD_S_PRIZ" (list (cld:e-line '(0 0) '(0.06 0) "0") (cld:e-line '(0.06 -0.12) '(0.06 0.12) "0")
                                 (cld:e-arc '(0.06 0) 0.12 (- (/ pi 2)) (/ pi 2) "0") (cld:e-line '(0.20 -0.10) '(0.20 0.10) "0")))
  (cld:defblk "CLD_S_PRIZE" (list (cld:e-line '(0 0) '(0.06 0) "0") (cld:e-line '(0.06 -0.12) '(0.06 0.12) "0")
                                  (cld:e-arc '(0.06 0) 0.12 (- (/ pi 2)) (/ pi 2) "0") (cld:e-dot '(0.11 0) 0.06 "0")
                                  (cld:e-line '(0.20 -0.10) '(0.20 0.10) "0")))
  (cld:defblk "CLD_S_PRIZU" (list (cld:e-line '(0 0) '(0.06 0) "0") (cld:e-line '(0.06 -0.12) '(0.06 0.12) "0")
                                  (cld:e-arc '(0.06 0) 0.12 (- (/ pi 2)) (/ pi 2) "0") (cld:b-txt '(0.11 0) 0.09 "U")))
  (cld:defblk "CLD_S_PRIZ3" (list (cld:e-line '(0 0) '(0.06 0) "0") (cld:e-line '(0.06 -0.14) '(0.06 0.14) "0")
                                  (cld:e-arc '(0.06 0) 0.14 (- (/ pi 2)) (/ pi 2) "0")
                                  (cld:e-line '(0.10 -0.06) '(0.18 -0.06) "0") (cld:e-line '(0.10 0.0) '(0.18 0.0) "0") (cld:e-line '(0.10 0.06) '(0.18 0.06) "0")))
  (cld:defblk "CLD_S_PGRUP" (list (cld:b-box 0.50 0.30) (cld:e-arc '(-0.13 -0.02) 0.08 0.0 pi "0") (cld:e-arc '(0.0 -0.02) 0.08 0.0 pi "0")
                                  (cld:e-arc '(0.13 -0.02) 0.08 0.0 pi "0") (cld:e-line '(-0.25 -0.08) '(0.25 -0.08) "0")))
  (foreach c '(("CLD_S_CK_KLIMA" "K") ("CLD_S_CK_FIRIN" "F") ("CLD_S_CK_BULASIK" "B") ("CLD_S_CK_CAMASIR" "\\U+00C7")
               ("CLD_S_CK_KURUTMA" "KM") ("CLD_S_CK_KOMBI" "KB") ("CLD_S_CK_DAVLUMBAZ" "D") ("CLD_S_CK_POMPA" "P")
               ("CLD_S_CK_ASPIRATOR" "A") ("CLD_S_CK_ASANSOR" "AS") ("CLD_S_CK_SARJ" "EV") ("CLD_S_CK_ISITICI" "IS")
               ("CLD_S_CK_TERMOSIFON" "TS") ("CLD_S_CK_MAKINE" "M"))
    (cld:defblk (car c) (list (cld:b-wallbox 0.24 0.24) (cld:e-solid '(0 -0.12) '(0.08 -0.12) '(0.08 0.12) '(0 0.12) "0")
                              (cld:b-txt '(0.16 0.0) 0.09 (cadr c)))))
  (cld:defblk "CLD_S_ANH1" (list (cld:e-circle '(0.10 0) 0.05 "0") (cld:e-line '(0.135 0.035) '(0.25 0.15) "0") (cld:e-line '(0.25 0.15) '(0.29 0.11) "0")))
  (cld:defblk "CLD_S_ANH2" (list (cld:e-circle '(0.10 0) 0.05 "0") (cld:e-line '(0.135 0.035) '(0.25 0.15) "0") (cld:e-line '(0.25 0.15) '(0.29 0.11) "0")
                                 (cld:e-line '(0.135 -0.035) '(0.25 -0.15) "0") (cld:e-line '(0.25 -0.15) '(0.29 -0.11) "0")))
  (cld:defblk "CLD_S_VAV" (list (cld:e-circle '(0.10 0) 0.05 "0") (cld:e-line '(0.135 0.035) '(0.25 0.15) "0") (cld:e-line '(0.25 0.15) '(0.29 0.11) "0")
                                (cld:e-line '(0.065 -0.035) '(-0.05 -0.15) "0") (cld:e-line '(-0.05 -0.15) '(-0.09 -0.11) "0")))
  (cld:defblk "CLD_S_BUAT" (list (cld:e-circle '(0 0) 0.05 "0")))
  ;; ---------------- PANOLAR
  (cld:defblk "CLD_S_TP" (list (cld:b-wallbox 0.16 0.50) (cld:e-solid '(0 -0.25) '(0.16 -0.25) '(0.16 0.25) '(0 -0.25) "0")))
  (cld:defblk "CLD_S_ADP" (list (cld:b-wallbox 0.30 0.90) (cld:e-solid '(0 -0.45) '(0.30 -0.45) '(0.30 0.45) '(0 0.45) "0")))
  (cld:defblk "CLD_S_KMP" (list (cld:b-wallbox 0.30 0.60) (cld:e-line '(0 -0.30) '(0.30 0.30) "0") (cld:b-txt '(0.15 -0.15) 0.10 "C")))
  (cld:defblk "CLD_S_KOLON" (list (cld:e-circle '(0 0) 0.15 "0") (cld:e-line '(-0.106 -0.106) '(0.106 0.106) "0")
                                  (cld:e-line '(0.106 0.106) '(0.02 0.106) "0") (cld:e-line '(0.106 0.106) '(0.106 0.02) "0")))
  (cld:defblk "CLD_S_OAP" (list (cld:b-wallbox 0.20 0.60) (cld:e-solid '(0 -0.30) '(0.20 -0.30) '(0.20 0.0) '(0 0.0) "0")))
  (cld:defblk "CLD_S_TRAFO" (list (cld:b-box 6.0 5.0) (cld:e-circle '(-0.45 0) 0.8 "0") (cld:e-circle '(0.45 0) 0.8 "0")))
  (cld:defblk "CLD_S_JEN" (list (cld:b-box 4.0 1.6) (cld:e-circle '(-1.2 0) 0.55 "0") (cld:b-txt '(-1.2 0) 0.5 "G")))
  ;; ---------------- TOPRAKLAMA / PARATONER
  (cld:defblk "CLD_S_TOP_FILIZ" (list (cld:e-circle '(0 0) 0.15 "0") (cld:e-dot '(0 0) 0.12 "0")))
  (cld:defblk "CLD_S_TOP_EPB" (list (cld:b-box 0.60 0.16) (cld:e-solid '(-0.30 -0.08) '(0.30 -0.08) '(0.30 0.08) '(-0.30 0.08) "0")
                                    (cld:e-line '(-0.2 -0.08) '(-0.2 -0.25) "0") (cld:e-line '(0 -0.08) '(0 -0.25) "0") (cld:e-line '(0.2 -0.08) '(0.2 -0.25) "0")))
  (cld:defblk "CLD_S_TOP_YEB" (list (cld:b-wallbox 0.10 0.30) (cld:e-solid '(0 -0.15) '(0.10 -0.15) '(0.10 0.15) '(0 0.15) "0")))
  (cld:defblk "CLD_S_TOP_KAZIK" (list (cld:e-line '(0 0.20) '(0 0) "0") (cld:e-line '(-0.15 0) '(0.15 0) "0")
                                      (cld:e-line '(-0.10 -0.05) '(0.10 -0.05) "0") (cld:e-line '(-0.05 -0.10) '(0.05 -0.10) "0")
                                      (cld:e-circle '(0 0.05) 0.25 "0")))
  (cld:defblk "CLD_S_TOP_OLCU" (append (list (cld:b-box 0.30 0.30)) (cld:b-x 0.15)))
  (cld:defblk "CLD_S_PAR_UC" (list (cld:e-circle '(0 0) 0.20 "0") (cld:e-solid '(-0.12 -0.08) '(0.12 -0.08) '(0.0 0.14) '(0.0 0.14) "0")))
  (cld:defblk "CLD_S_PAR_INIS" (list (cld:e-circle '(0 0) 0.15 "0") (cld:e-dot '(0 0) 0.08 "0")
                                     (cld:e-line '(0.0 -0.15) '(0.0 -0.40) "0") (cld:e-line '(-0.08 -0.30) '(0.0 -0.40) "0") (cld:e-line '(0.08 -0.30) '(0.0 -0.40) "0")))
  (cld:defblk "CLD_S_PAR_KLEMENS" (list (cld:b-box 0.25 0.25) (cld:e-solid '(-0.125 -0.125) '(0.125 -0.125) '(0.125 0.125) '(-0.125 -0.125) "0")))
  ;; ---------------- MEKANIK
  (cld:defblk "CLD_S_KASET" (append (list (cld:b-box 0.84 0.84) (cld:b-box 0.56 0.56)) (cld:b-x 0.28)))
  (cld:defblk "CLD_S_VRFOUT" (list (cld:b-box 1.30 0.75) (cld:e-circle '(-0.3 0) 0.28 "0") (cld:e-circle '(0.3 0) 0.28 "0")))
  (cld:defblk "CLD_S_HRV" (list (cld:b-box 1.40 0.80) (cld:e-line '(-0.7 -0.4) '(0.7 0.4) "0") (cld:e-line '(-0.7 0.4) '(0.7 -0.4) "0") (cld:b-txt '(0 0.25) 0.15 "HRV")))
  (cld:defblk "CLD_S_MENFEZ" (append (list (cld:b-box 0.60 0.60) (cld:b-box 0.30 0.30)) (cld:b-x 0.30)))
  (cld:defblk "CLD_S_EMIS" (list (cld:b-box 0.40 0.40) (cld:e-line '(-0.2 -0.1) '(0.2 -0.1) "0") (cld:e-line '(-0.2 0.0) '(0.2 0.0) "0") (cld:e-line '(-0.2 0.1) '(0.2 0.1) "0")))
  (cld:defblk "CLD_S_CATIFAN" (list (cld:e-circle '(0 0) 0.60 "0") (cld:e-circle '(0 0) 0.15 "0") (cld:e-line '(0 0) '(0.5 0.25) "0")
                                    (cld:e-line '(0 0) '(-0.5 0.25) "0") (cld:e-line '(0 0) '(0 -0.55) "0")))
  (cld:defblk "CLD_S_PANJUR" (list (cld:b-wallbox 0.20 1.20) (cld:e-line '(0 -0.4) '(0.2 -0.3) "0") (cld:e-line '(0 0.0) '(0.2 0.1) "0") (cld:e-line '(0 0.4) '(0.2 0.5) "0")))
  (cld:defblk "CLD_S_RADYANT" (list (cld:e-pl '((-3.0 -0.15) (3.0 -0.15) (3.0 0.15) (-3.0 0.15)) T 0.0 "0") (cld:e-line '(-3.0 0) '(2.6 0) "0") (cld:b-box 0.6 0.4)))
  (cld:defblk "CLD_S_SIGFAN" (list (cld:b-box 0.80 0.60) (cld:e-circle '(0 0) 0.22 "0") (cld:b-txt '(0 -0.2) 0.10 "S")))
  ;; ---------------- SIHHI TESISAT
  (cld:defblk "CLD_S_PK" (append (list (cld:e-circle '(0 0) 0.10 "0")) (cld:b-x 0.07)))
  (cld:defblk "CLD_S_TSK" (list (cld:e-circle '(0 0) 0.08 "0") (cld:e-dot '(0 0) 0.05 "0")))
  (cld:defblk "CLD_S_YK" (list (cld:e-circle '(0 0) 0.10 "0") (cld:e-circle '(0 0) 0.05 "0")))
  (cld:defblk "CLD_S_YS" (list (cld:b-box 0.18 0.18) (cld:e-circle '(0 0) 0.06 "0") (cld:e-line '(-0.06 0) '(0.06 0) "0")))
  (cld:defblk "CLD_S_SUSAYAC" (list (cld:e-circle '(0 0) 0.12 "0") (cld:e-line '(-0.12 0) '(0.12 0) "0") (cld:b-txt '(0 0.05) 0.06 "m3")))
  (cld:defblk "CLD_S_ROGAR" (list (cld:b-box 0.60 0.60) (cld:e-circle '(0 0) 0.22 "0")))
  (cld:defblk "CLD_S_DEPO" (append (list (cld:b-box 1.20 0.80)) (list (cld:e-line '(-0.6 -0.4) '(0.6 0.4) "0") (cld:e-line '(-0.6 0.4) '(0.6 -0.4) "0"))))
  (cld:defblk "CLD_S_KLOZET" (list (cld:e-pl '((-0.18 0.30) (0.18 0.30) (0.18 0.12) (-0.18 0.12)) T 0.0 "0")
                                   (cld:e-circle '(0 -0.08) 0.18 "0")))
  (cld:defblk "CLD_S_LAVABO" (list (cld:b-box 0.50 0.40) (cld:e-circle '(0 -0.03) 0.13 "0")))
  (cld:defblk "CLD_S_ABDEST" (list (cld:b-box 0.40 0.30) (cld:e-circle '(0 0.05) 0.05 "0") (cld:e-line '(0 0.05) '(0 -0.12) "0")))
  (cld:defblk "CLD_S_YD" (list (cld:b-wallbox 0.25 0.80) (cld:e-solid '(0 -0.40) '(0.25 -0.40) '(0.25 -0.10) '(0 -0.10) "0")
                              (cld:b-txt '(0.125 0.15) 0.12 "YD")))
  (cld:defblk "CLD_S_DUS" (append (list (cld:b-box 0.90 0.90) (cld:e-circle '(0 0) 0.06 "0")) (cld:b-x 0.45)))
  T)


(setq *cld-u* 100.0)
(setq *cld-ext* (list 0.0 0.0 1.0))

(defun cld:ops-p2_kuvvetli_akim-layers () (cld:play (quote (("LY" "CLD-P2-KAK-YAZI" 7 nil -3) ("LY" "CLD-P2-KAK-PAFTA" 7 nil 50) ("LY" "CLD-P2-KAK-ALTLIK" 8 nil 13) ("LY" "CLD-P2-KAK-TABLO" 7 nil -3) ("LY" "CLD-P2-KAK-PANO" 1 nil 50) ("LY" "CLD-P2-KAK-BESLEME" 1 "CLD_UZUNKESIK" 50) ("LY" "CLD-P2-KAK-BARA" 6 nil 70) ("LY" "CLD-P2-KAK-TRAFO-JEN" 1 nil 50) ("LY" "CLD-P2-KAK-CEPHE-AYD" 2 nil -3)))))
(defun cld:ops-p2_kuvvetli_akim-1 () (cld:play (quote (
   ("BK" "CLD_P2_MIMARI_1K_V2" ((nil (7250.3 7995.7) (7341.0 7995.7)) (nil (7271.6 7979.5) (7271.6 8011.8)) (T (7282.4 7995.7) (7282.0 7998.5) (7280.9 8001.1) (7279.2 8003.3) (7277.0 8005.0) (7274.4 8006.1) (7271.6 8006.4) (7268.8 8006.1) (7266.2 8005.0) (7264.0 8003.3) (7262.2 8001.1) (7261.2 7998.5) (7260.8 7995.7) (7261.2 7992.9) (7262.2 7990.3) (7264.0 7988.0) (7266.2 7986.3) (7268.8 7985.2) (7271.6 7984.9) (7274.4 7985.2) (7277.0 7986.3) (7279.2 7988.0) (7280.9 7990.3) (7282.0 7992.9) (7282.4 7995.7)) (nil (7176.3 8201.6) (7267.0 8201.6)) (nil (7197.5 8185.4) (7197.5 8217.8)) (T (7208.3 8201.6) (7207.9 8204.4) (7206.9 8207.0) (7205.2 8209.2) (7202.9 8210.9) (7200.3 8212.0) (7197.5 8212.4) (7194.7 8212.0) (7192.1 8210.9) (7189.9 8209.2) (7188.2 8207.0) (7187.1 8204.4) (7186.7 8201.6) (7187.1 8198.8) (7188.2 8196.2) (7189.9 8193.9) (7192.1 8192.2) (7194.7 8191.2) (7197.5 8190.8) (7200.3 8191.2) (7202.9 8192.2) (7205.2 8193.9) (7206.9 8196.2) (7207.9 8198.8) (7208.3 8201.6)) (nil (7329.4 7939.8) (7325.4 7939.8)) (nil (7329.4 7924.8) (7329.4 7939.8)) (nil (7239.4 7924.8) (7239.4 7939.8)) (nil (7322.6 7845.4) (7326.6 7845.4)) (nil (7322.6 7924.8) (7322.6 7845.4)) (nil (7326.6 7845.4) (7326.6 7924.8)) (nil (7325.4 7928.8) (7325.4 7939.8)) (nil (7326.6 7928.8) (7325.4 7928.8)) (nil (7326.6 7924.8) (7326.6 7928.8)) (nil (7329.4 7924.8) (7326.6 7924.8)) (nil (7329.4 7939.8) (7329.4 7924.8)) (nil (7239.4 7939.8) (7243.4 7939.8)) (nil (7239.4 7924.8) (7239.4 7939.8)) (nil (7242.2 7924.8) (7239.4 7924.8)) (nil (7242.2 7928.8) (7242.2 7924.8)) (nil (7243.4 7928.8) (7242.2 7928.8)) (nil (7243.4 7939.8) (7243.4 7928.8)) (nil (7242.2 7924.8) (7252.8 7896.0) (7271.8 7871.7) (7297.1 7854.3) (7326.6 7845.4)) (nil (7239.4 7924.8) (7239.4 7939.8)) (nil (7329.4 7924.8) (7329.4 7939.8)) (nil (7329.4 7939.8) (7329.4 7924.8)) (nil (7329.4 8059.8) (7325.4 8059.8)) (nil (7329.4 8074.8) (7329.4 8059.8)) (nil (7239.4 8074.8) (7239.4 8059.8)) (nil (7322.6 8154.2) (7326.6 8154.2)) (nil (7322.6 8074.8) (7322.6 8154.2)) (nil (7326.6 8154.2) (7326.6 8074.8)) (nil (7325.4 8070.8) (7325.4 8059.8)) (nil (7326.6 8070.8) (7325.4 8070.8)) (nil (7326.6 8074.8) (7326.6 8070.8)) (nil (7329.4 8074.8) (7326.6 8074.8)) (nil (7329.4 8059.8) (7329.4 8074.8)) (nil (7239.4 8059.8) (7243.4 8059.8)) (nil (7239.4 8074.8) (7239.4 8059.8)) (nil (7242.2 8074.8) (7239.4 8074.8)) (nil (7242.2 8070.8) (7242.2 8074.8)) (nil (7243.4 8070.8) (7242.2 8070.8)) (nil (7243.4 8059.8) (7243.4 8070.8)) (nil (7326.6 8154.2) (7297.1 8145.4) (7271.8 8128.0) (7252.8 8103.7) (7242.2 8074.8)) (nil (7239.4 8074.8) (7239.4 8059.8)) (nil (7329.4 8074.8) (7329.4 8059.8)) (nil (7330.5 8074.8) (7330.5 8082.1)) (nil (7020.1 8074.8) (7016.1 8074.8)) (nil (7020.1 8059.8) (7020.1 8074.8)) (nil (6930.1 8059.8) (6930.1 8074.8)) (nil (7013.3 7980.4) (7017.3 7980.4)) (nil (7013.3 8059.8) (7013.3 7980.4)) (nil (7017.3 7980.4) (7017.3 8059.8)) (nil (7016.1 8063.8) (7016.1 8074.8)) (nil (7017.3 8063.8) (7016.1 8063.8)) (nil (7017.3 8059.8) (7017.3 8063.8)) (nil (7020.1 8059.8) (7017.3 8059.8)) (nil (7020.1 8074.8) (7020.1 8059.8)) (nil (6930.1 8074.8) (6934.1 8074.8)) (nil (6930.1 8059.8) (6930.1 8074.8)) (nil (6932.9 8059.8) (6930.1 8059.8)) (nil (6932.9 8063.8) (6932.9 8059.8)) (nil (6934.1 8063.8) (6932.9 8063.8)) (nil (6934.1 8074.8) (6934.1 8063.8)) (nil (6932.9 8059.8) (6943.5 8030.9) (6962.5 8006.6) (6987.8 7989.2) (7017.3 7980.4)) (nil (6930.1 8059.8) (6930.1 8074.8)) (nil (7020.1 8059.8) (7020.1 8074.8)) (nil (7021.2 8059.8) (7021.2 8052.4)) (nil (7200.1 7924.8) (7196.1 7924.8)) (nil (7200.1 7939.8) (7200.1 7924.8)) (nil (7110.1 7939.8) (7110.1 7924.8)) (nil (7193.3 8019.2) (7197.3 8019.2)) (nil (7193.3 7939.8) (7193.3 8019.2)) (nil (7197.3 8019.2) (7197.3 7939.8)) (nil (7196.1 7935.8) (7196.1 7924.8)) (nil (7197.3 7935.8) (7196.1 7935.8)) (nil (7197.3 7939.8) (7197.3 7935.8)) (nil (7200.1 7939.8) (7197.3 7939.8)) (nil (7200.1 7924.8) (7200.1 7939.8)) (nil (7110.1 7924.8) (7114.1 7924.8)) (nil (7110.1 7939.8) (7110.1 7924.8)) (nil (7112.9 7939.8) (7110.1 7939.8)) (nil (7112.9 7935.8) (7112.9 7939.8)) (nil (7114.1 7935.8) (7112.9 7935.8)) (nil (7114.1 7924.8) (7114.1 7935.8)) (nil (7197.3 8019.2) (7167.9 8010.4) (7142.5 7993.0) (7123.6 7968.7) (7112.9 7939.8)) (nil (7110.1 7939.8) (7110.1 7924.8)) (nil (7200.1 7939.8) (7200.1 7924.8)) (nil (7201.3 7939.8) (7201.3 7947.1)) (nil (7035.1 7939.8) (7035.1 8059.8)) (nil (7020.1 7939.8) (7020.1 8059.8)) (nil (7329.4 8059.8) (7329.4 8074.8)) (nil (7200.1 7924.8) (7242.2 7924.8)) (nil (7325.4 7939.8) (7542.7 7939.8)) (nil (7226.4 7939.8) (7243.4 7939.8)) (nil (7193.3 7939.8) (7211.4 7939.8)) (nil (6843.9 7939.8) (7112.9 7939.8)) (nil (7322.7 8074.8) (7406.4 8074.9)) (nil (7016.1 8074.8) (7242.2 8074.8)) (nil (6883.3 8074.7) (6934.1 8074.7)) (nil (7329.4 8059.8) (7421.5 8059.9)) (nil (7226.4 8059.8) (7239.4 8059.8)) (nil (7013.3 8059.8) (7211.4 8059.8)) (nil (6883.3 8059.7) (6932.9 8059.7)) (nil (7541.4 7939.8) (7520.0 7939.8)) (nil (7211.4 8059.8) (7211.4 7939.8)) (nil (7226.4 8059.8) (7226.4 7939.8)) (nil (7346.4 8059.8) (7346.4 7939.8)) (nil (7371.4 8059.8) (7371.4 7939.8)) (nil (7396.4 8059.8) (7396.4 7939.8)) (nil (7421.4 8059.8) (7421.4 7939.8)) (nil (7421.4 8084.8) (7531.4 8084.8)) (nil (7421.4 8109.8) (7531.4 8109.8)) (nil (7421.4 8134.8) (7531.4 8134.8)) (nil (7421.4 8159.8) (7531.4 8159.8)) (nil (7421.4 8184.8) (7531.4 8184.8)) (nil (7421.4 8209.8) (7531.4 8209.8)) (nil (7421.4 8234.8) (7531.4 8234.8)) (nil (7421.4 8259.8) (7531.4 8259.8)) (nil (7421.4 8284.8) (7531.4 8284.8)) (nil (7421.4 8309.8) (7531.4 8309.8)) (nil (7421.4 8334.8) (7541.4 8334.8)) (nil (7421.4 8059.8) (7421.4 8049.8)) (nil (7541.4 8059.8) (7421.4 8059.8)) (nil (7421.4 8059.8) (7421.4 8049.8)) (nil (7421.4 8059.8) (7421.4 8049.8)) (nil (7421.4 8084.8) (7541.4 8084.8)) (nil (7421.4 8109.8) (7541.4 8109.8)) (nil (7421.4 8134.8) (7541.4 8134.8)) (nil (7421.4 8159.8) (7541.4 8159.8)) (nil (7421.4 8184.8) (7541.4 8184.8)) (nil (7421.4 8209.8) (7541.4 8209.8)) (nil (7421.4 8234.8) (7541.4 8234.8)) (nil (7421.4 8259.8) (7541.4 8259.8)) (nil (7421.4 8284.8) (7541.4 8284.8)) (nil (7421.4 8309.8) (7541.4 8309.8)) (nil (7421.4 8334.8) (7538.4 8334.8)) (nil (7421.4 8059.8) (7421.4 8334.8)) (nil (7421.4 8304.8) (7421.4 8319.8)) (nil (8693.0 2066.9) (6345.8 5352.9) (1517.3 6484.5) (1058.6 6932.1) (5479.1 8059.4) (5998.2 8156.3) (7170.0 8375.1) (7688.3 8471.9) (8852.2 8689.2) (8852.0 5259.7) (8851.8 2089.4)) (nil (8689.1 2059.4) (6341.4 5346.3) (1513.5 6477.7) (1043.8 6936.1) (5477.5 8066.7) (5996.8 8163.7) (7168.6 8382.5) (7686.9 8479.3) (8859.7 8698.3) (8859.5 5259.7) (8859.3 2089.4)) (nil (6873.3 5242.1) (6425.0 5242.1)) (nil (6873.3 5257.1) (6414.3 5257.1)) (nil (7413.3 8420.5) (7041.2 8351.1)) (nil (6828.9 7670.1) (7420.9 7670.3)) (nil (6828.9 7655.1) (7420.9 7655.3)) (nil (6843.9 7655.1) (6843.9 8312.3)) (nil (6828.9 7655.1) (6828.9 8312.3)) (nil (7411.2 8431.9) (7411.1 8432.2)) (nil (7411.1 8431.9) (7411.1 8432.2)) (nil (7398.3 7655.0) (7399.5 7655.0)) (nil (6893.3 5242.1) (6893.3 6260.2)) (nil (6873.3 5242.1) (6873.3 6260.2)) (nil (1023.6 6952.3) (1025.0 6946.5)) (nil (5807.7 6742.9) (5898.4 6742.9)) (nil (5829.0 6726.7) (5829.0 6759.1)) (T (5839.8 6742.9) (5839.4 6745.7) (5838.3 6748.3) (5836.6 6750.5) (5834.4 6752.2) (5831.8 6753.3) (5829.0 6753.7) (5826.2 6753.3) (5823.6 6752.2) (5821.3 6750.5) (5819.6 6748.3) (5818.6 6745.7) (5818.2 6742.9) (5818.6 6740.1) (5819.6 6737.5) (5821.3 6735.3) (5823.6 6733.5) (5826.2 6732.5) (5829.0 6732.1) (5831.8 6732.5) (5834.4 6733.5) (5836.6 6735.3) (5838.3 6737.5) (5839.4 6740.1) (5839.8 6742.9)) (nil (7981.8 5937.5) (8072.6 5937.5)) (nil (8003.1 5921.4) (8003.1 5953.7)) (T (8013.9 5937.5) (8013.5 5940.3) (8012.5 5942.9) (8010.7 5945.1) (8008.5 5946.9) (8005.9 5947.9) (8003.1 5948.3) (8000.3 5947.9) (7997.7 5946.9) (7995.5 5945.1) (7993.8 5942.9) (7992.7 5940.3) (7992.3 5937.5) (7992.7 5934.7) (7993.8 5932.1) (7995.5 5929.9) (7997.7 5928.2) (8000.3 5927.1) (8003.1 5926.7) (8005.9 5927.1) (8008.5 5928.2) (8010.7 5929.9) (8012.5 5932.1) (8013.5 5934.7) (8013.9 5937.5)) (nil (7406.4 8074.9) (7406.4 8421.4)) (nil (7406.4 7654.4) (7406.4 7924.8)) (nil (7421.3 8059.9) (7421.4 8421.4)) (nil (7421.4 7654.4) (7421.4 7924.8)) (nil (6893.3 6919.4) (6893.3 7655.1)) (nil (6873.3 6919.4) (6873.3 7655.1)) (nil (6893.3 6319.4) (6893.3 6859.4)) (nil (6873.3 6319.4) (6873.3 6859.4)) (nil (8726.2 8673.7) (8728.0 8661.8)) (nil (8554.1 8641.2) (8555.9 8629.3)) (nil (8627.8 8655.6) (8629.5 8643.7)) (T (8859.7 5527.1) (8859.7 5530.1) (8849.7 5530.1) (8849.7 5527.1)) (T (8859.7 5523.1) (8859.7 5530.1) (8861.7 5530.1) (8861.7 5523.1)) (T (8847.7 5523.0) (8847.7 5530.0) (8849.7 5530.1) (8849.7 5523.1)) (T (8859.7 5627.1) (8859.7 5624.1) (8849.7 5624.0) (8849.7 5627.0)) (T (8859.7 5631.1) (8859.7 5624.1) (8861.7 5624.1) (8861.7 5631.1)) (T (8847.7 5631.0) (8847.7 5624.0) (8849.7 5624.0) (8849.7 5631.0)) (T (8861.7 5530.1) (8861.7 5624.1) (8856.7 5624.1) (8856.7 5530.1)) (nil (8861.7 5624.1) (8861.7 5530.1) (8955.7 5530.1)) (nil (8861.7 5624.1) (8886.0 5620.9) (8908.7 5611.5) (8928.1 5596.5) (8943.1 5577.1) (8952.5 5554.4) (8955.7 5530.1)) (T (7615.2 3576.3) (7613.5 3578.7) (7605.3 3572.9) (7607.1 3570.4)) (T (7617.5 3573.0) (7613.5 3578.7) (7615.1 3579.9) (7619.2 3574.2)) (T (7607.8 3566.0) (7603.7 3571.7) (7605.3 3572.9) (7609.4 3567.2)) (T (7556.9 3657.5) (7558.6 3655.0) (7550.5 3649.2) (7548.8 3651.6)) (T (7554.5 3660.7) (7558.6 3655.0) (7560.3 3656.2) (7556.2 3661.9)) (T (7544.8 3653.7) (7548.9 3648.0) (7550.5 3649.2) (7546.4 3654.9)) (T (7615.1 3579.9) (7560.3 3656.2) (7556.2 3653.3) (7611.0 3576.9)) (nil (7560.3 3656.2) (7615.1 3579.9) (7691.4 3634.7)) (nil (7560.3 3656.2) (7581.9 3667.8) (7605.8 3673.4) (7630.3 3672.6) (7653.8 3665.5) (7674.6 3652.6) (7691.4 3634.7))) ((6925.9 8023.5 22.0 "ABDESTHANE") (6925.9 7987.5 16.0 "1,9 m\\U+00B2") (7095.1 8023.6 22.0 "ABDESTHANE") (7095.1 7987.6 16.0 "1,6 m\\U+00B2") (7125.1 7779.9 22.0 "KADIN MESC\\U+0130T") (7125.1 7743.9 16.0 "15,0 m\\U+00B2") (7125.1 8285.5 22.0 "ERKEK MESC\\U+0130T") (7125.1 8249.5 16.0 "15,9 m\\U+00B2")))
   ("BK" "CLD_P2_MIMARI_ZK_V2" ((nil (7626.7 7918.6) (7486.7 7918.6)) (nil (7606.7 8448.2) (7606.7 7938.6)) (nil (7606.7 7938.6) (7486.7 7938.6)) (nil (7486.7 8088.6) (7596.7 8088.6)) (nil (7486.7 8113.6) (7596.7 8113.6)) (nil (7486.7 8138.6) (7596.7 8138.6)) (nil (7486.7 8163.6) (7596.7 8163.6)) (nil (7486.7 8188.6) (7596.7 8188.6)) (nil (7486.7 8213.6) (7596.7 8213.6)) (nil (7486.7 8238.6) (7596.7 8238.6)) (nil (7486.7 8263.6) (7596.7 8263.6)) (nil (7486.7 8288.6) (7596.7 8288.6)) (nil (7486.7 8313.6) (7596.7 8313.6)) (nil (7486.7 8338.6) (7606.7 8338.6)) (nil (7606.7 8063.6) (7486.7 8063.6)) (nil (7486.7 8088.6) (7606.7 8088.6)) (nil (7486.7 8113.6) (7606.7 8113.6)) (nil (7486.7 8138.6) (7606.7 8138.6)) (nil (7486.7 8163.6) (7606.7 8163.6)) (nil (7486.7 8188.6) (7606.7 8188.6)) (nil (7486.7 8213.6) (7606.7 8213.6)) (nil (7486.7 8238.6) (7606.7 8238.6)) (nil (7486.7 8263.6) (7606.7 8263.6)) (nil (7486.7 8288.6) (7606.7 8288.6)) (nil (7486.7 8313.6) (7606.7 8313.6)) (nil (7486.7 8338.6) (7603.7 8338.6)) (nil (7486.7 8063.6) (7486.7 8338.6)) (nil (7486.7 8308.6) (7486.7 8323.6)) (nil (8849.7 2070.6) (8758.3 2070.6) (6411.2 5356.7) (1582.6 6488.3) (1124.0 6935.9) (5544.5 8063.1) (6063.5 8160.0) (7235.3 8378.8) (7753.6 8475.6) (8917.5 8693.0) (8917.3 5263.4) (8917.2 2093.1)) (nil (8849.7 2063.1) (8754.5 2063.1) (6406.7 5350.0) (1578.9 6481.4) (1109.2 6939.9) (5542.9 8070.4) (6062.2 8167.4) (7233.9 8386.2) (7752.3 8483.0) (8925.0 8702.0) (8924.8 5263.4) (8924.7 2093.1)) (nil (6938.7 5245.8) (6490.4 5245.8)) (nil (6938.7 5260.8) (6479.6 5260.8)) (nil (7017.5 8286.0) (7006.6 8345.1)) (nil (7274.7 7878.9) (7274.7 7718.9)) (nil (7284.7 7868.9) (7284.7 7718.9)) (nil (7174.2 7868.8) (7174.2 7718.8)) (nil (7164.2 7868.8) (7164.2 7718.8)) (nil (7122.3 8269.1) (7106.5 8354.8)) (nil (7064.2 7868.8) (7064.2 7718.8)) (nil (7054.2 7868.8) (7054.2 7718.8)) (nil (7426.3 8063.6) (7426.3 7718.9)) (nil (7426.3 8353.6) (7426.3 8063.6)) (nil (7274.7 7878.8) (6954.2 7878.8)) (nil (7426.3 7878.9) (7274.7 7878.9)) (nil (7054.2 7868.8) (6954.2 7868.8)) (nil (7164.2 7868.8) (7064.2 7868.8)) (nil (7264.2 7868.8) (7174.2 7868.8)) (nil (7426.3 7868.9) (7284.7 7868.9)) (nil (6954.2 7718.8) (7426.3 7718.9)) (nil (7168.0 8306.1) (7168.0 8150.4)) (nil (7148.0 8302.4) (7148.0 8170.4)) (nil (6954.2 8279.2) (6954.2 7718.8)) (nil (7168.0 8150.4) (6954.2 8150.4)) (nil (7148.0 8170.4) (6954.2 8170.4)) (nil (7017.5 8286.0) (6955.0 8274.5)) (nil (7148.0 8302.4) (7117.2 8296.8)) (nil (7426.3 8353.6) (7168.0 8306.1)) (nil (6981.3 8344.4) (6894.2 8328.4)) (nil (7478.6 8424.3) (7106.5 8354.8)) (nil (6894.2 7658.8) (7486.3 7659.0)) (nil (6894.2 7658.8) (6894.2 8316.0)) (nil (7476.5 8435.6) (7476.4 8435.9)) (nil (7463.6 7658.8) (7464.9 7658.8)) (nil (6958.7 5245.8) (6958.7 6263.9)) (nil (6938.7 5245.8) (6938.7 6263.9)) (nil (1088.9 6956.1) (1090.4 6950.3)) (nil (5873.1 6746.6) (5963.8 6746.6)) (nil (5894.3 6730.4) (5894.3 6762.8)) (T (5905.1 6746.6) (5904.7 6749.4) (5903.7 6752.0) (5902.0 6754.2) (5899.7 6756.0) (5897.1 6757.0) (5894.3 6757.4) (5891.5 6757.0) (5888.9 6756.0) (5886.7 6754.2) (5885.0 6752.0) (5883.9 6749.4) (5883.5 6746.6) (5883.9 6743.8) (5885.0 6741.2) (5886.7 6739.0) (5888.9 6737.3) (5891.5 6736.2) (5894.3 6735.8) (5897.1 6736.2) (5899.7 6737.3) (5902.0 6739.0) (5903.7 6741.2) (5904.7 6743.8) (5905.1 6746.6)) (nil (8047.2 5941.3) (8137.9 5941.3)) (nil (8068.5 5925.1) (8068.5 5957.4)) (T (8079.3 5941.3) (8078.9 5944.1) (8077.8 5946.6) (8076.1 5948.9) (8073.9 5950.6) (8071.3 5951.7) (8068.5 5952.0) (8065.7 5951.7) (8063.1 5950.6) (8060.9 5948.9) (8059.1 5946.6) (8058.1 5944.1) (8057.7 5941.3) (8058.1 5938.5) (8059.1 5935.9) (8060.9 5933.6) (8063.1 5931.9) (8065.7 5930.9) (8068.5 5930.5) (8071.3 5930.9) (8073.9 5931.9) (8076.1 5933.6) (8077.8 5935.9) (8078.9 5938.5) (8079.3 5941.3)) (nil (7486.7 7658.1) (7486.7 8425.2)) (nil (6986.2 7658.1) (7486.7 7658.1)) (nil (6958.7 6923.1) (6958.7 7613.1)) (nil (6938.7 6923.1) (6938.7 7613.1)) (nil (6958.7 6323.1) (6958.7 6863.1)) (nil (6938.7 6323.1) (6938.7 6863.1)) (nil (8791.6 8677.5) (8793.3 8665.6)) (nil (8619.5 8644.9) (8621.2 8633.1)) (nil (8693.2 8659.4) (8694.9 8647.5)) (nil (8754.5 2063.1) (6406.7 5350.0) (1578.9 6481.4) (1109.2 6939.9) (5542.9 8070.4) (6062.2 8167.4) (7233.9 8386.2) (7752.3 8483.0) (8925.0 8702.0) (8924.8 5263.4) (8924.7 2093.1)) (T (1808.0 7119.5) (1805.1 7118.7) (1807.6 7109.0) (1810.5 7109.8)) (T (1811.9 7120.5) (1805.1 7118.7) (1804.6 7120.7) (1811.4 7122.4)) (T (1814.8 7108.8) (1808.0 7107.1) (1807.6 7109.0) (1814.3 7110.8)) (T (1711.1 7094.8) (1714.0 7095.5) (1716.5 7085.8) (1713.6 7085.1)) (T (1707.2 7093.8) (1714.0 7095.5) (1713.5 7097.4) (1706.7 7095.7)) (T (1710.2 7082.2) (1717.0 7083.9) (1716.5 7085.8) (1709.7 7084.1)) (T (1804.6 7120.7) (1713.5 7097.4) (1714.7 7092.6) (1805.8 7115.8)) (nil (1713.5 7097.4) (1804.6 7120.7) (1781.4 7211.8)) (nil (1713.5 7097.4) (1710.6 7121.8) (1714.1 7146.1) (1723.8 7168.7) (1738.9 7187.9) (1758.6 7202.6) (1781.4 7211.8)) (T (6288.5 8209.7) (6291.4 8210.2) (6293.3 8200.4) (6290.3 8199.8)) (T (6284.5 8208.9) (6291.4 8210.2) (6291.1 8212.2) (6284.2 8210.9)) (T (6286.8 8197.1) (6293.6 8198.4) (6293.3 8200.4) (6286.4 8199.1)) (T (6386.8 8228.0) (6383.8 8227.5) (6385.7 8217.6) (6388.6 8218.2)) (T (6390.7 8228.8) (6383.8 8227.5) (6383.5 8229.4) (6390.3 8230.7)) (T (6392.9 8217.0) (6386.0 8215.7) (6385.7 8217.6) (6392.5 8218.9)) (T (6291.1 8212.2) (6383.5 8229.4) (6384.4 8224.5) (6292.0 8207.3)) (nil (6383.5 8229.4) (6291.1 8212.2) (6273.8 8304.6)) (nil (6383.5 8229.4) (6375.9 8252.8) (6362.5 8273.3) (6344.2 8289.7) (6322.3 8300.8) (6298.3 8305.9) (6273.8 8304.6)) (T (7148.0 8175.2) (7148.0 8178.2) (7168.0 8178.2) (7168.0 8175.2)) (T (7148.0 8171.2) (7148.0 8178.2) (7146.0 8178.2) (7146.0 8171.2)) (T (7170.0 8171.2) (7170.0 8178.2) (7168.0 8178.2) (7168.0 8171.2)) (T (7148.0 8275.2) (7148.0 8272.2) (7168.0 8272.2) (7168.0 8275.2)) (T (7148.0 8279.2) (7148.0 8272.2) (7146.0 8272.2) (7146.0 8279.2)) (T (7170.0 8279.2) (7170.0 8272.2) (7168.0 8272.2) (7168.0 8279.2)) (T (7146.0 8178.2) (7146.0 8272.2) (7151.0 8272.2) (7151.0 8178.2)) (nil (7146.0 8272.2) (7146.0 8178.2) (7052.0 8178.2)) (nil (7146.0 8272.2) (7121.6 8269.0) (7099.0 8259.6) (7079.5 8244.6) (7064.6 8225.2) (7055.2 8202.5) (7052.0 8178.2)) (T (7288.7 7878.9) (7291.7 7878.9) (7291.7 7868.9) (7288.7 7868.9)) (T (7284.7 7878.9) (7291.7 7878.9) (7291.7 7880.9) (7284.7 7880.9)) (T (7284.7 7866.9) (7291.7 7866.9) (7291.7 7868.9) (7284.7 7868.9)) (T (7378.7 7878.9) (7375.7 7878.9) (7375.7 7868.9) (7378.7 7868.9)) (T (7382.7 7878.9) (7375.7 7878.9) (7375.7 7880.9) (7382.7 7880.9)) (T (7382.7 7866.9) (7375.7 7866.9) (7375.7 7868.9) (7382.7 7868.9)) (T (7291.7 7880.9) (7375.7 7880.9) (7375.7 7875.9) (7291.7 7875.9)) (nil (7375.7 7880.9) (7291.7 7880.9) (7291.7 7964.9)) (nil (7291.7 7964.9) (7313.5 7962.0) (7333.7 7953.6) (7351.1 7940.3) (7364.5 7922.9) (7372.9 7902.6) (7375.7 7880.9)) (T (7178.3 7878.8) (7181.3 7878.8) (7181.2 7868.8) (7178.2 7868.8)) (T (7174.3 7878.8) (7181.3 7878.8) (7181.3 7880.8) (7174.3 7880.8)) (T (7174.2 7866.8) (7181.2 7866.8) (7181.2 7868.8) (7174.2 7868.8)) (T (7258.2 7878.8) (7255.2 7878.8) (7255.2 7868.8) (7258.2 7868.8)) (T (7262.2 7878.8) (7255.2 7878.8) (7255.3 7880.8) (7262.3 7880.8)) (T (7262.2 7866.8) (7255.2 7866.8) (7255.2 7868.8) (7262.2 7868.8)) (T (7181.3 7880.8) (7255.3 7880.8) (7255.2 7875.8) (7181.2 7875.8)) (nil (7255.3 7880.8) (7181.3 7880.8) (7181.3 7954.8)) (nil (7181.3 7954.8) (7200.4 7952.3) (7218.3 7944.9) (7233.6 7933.1) (7245.3 7917.8) (7252.7 7900.0) (7255.3 7880.8)) (T (7068.3 7878.8) (7071.3 7878.8) (7071.2 7868.8) (7068.2 7868.8)) (T (7064.3 7878.8) (7071.3 7878.8) (7071.3 7880.8) (7064.3 7880.8)) (T (7064.2 7866.8) (7071.2 7866.8) (7071.2 7868.8) (7064.2 7868.8)) (T (7148.2 7878.8) (7145.2 7878.8) (7145.2 7868.8) (7148.2 7868.8)) (T (7152.2 7878.8) (7145.2 7878.8) (7145.3 7880.8) (7152.3 7880.8)) (T (7152.2 7866.8) (7145.2 7866.8) (7145.2 7868.8) (7152.2 7868.8)) (T (7071.3 7880.8) (7145.3 7880.8) (7145.2 7875.8) (7071.2 7875.8)) (nil (7145.3 7880.8) (7071.3 7880.8) (7071.3 7954.8)) (nil (7071.3 7954.8) (7090.4 7952.3) (7108.3 7944.9) (7123.6 7933.1) (7135.3 7917.8) (7142.7 7900.0) (7145.3 7880.8)) (T (6968.3 7878.8) (6971.3 7878.8) (6971.2 7868.8) (6968.2 7868.8)) (T (6964.3 7878.8) (6971.3 7878.8) (6971.3 7880.8) (6964.3 7880.8)) (T (6964.2 7866.8) (6971.2 7866.8) (6971.2 7868.8) (6964.2 7868.8)) (T (7048.2 7878.8) (7045.2 7878.8) (7045.2 7868.8) (7048.2 7868.8)) (T (7052.2 7878.8) (7045.2 7878.8) (7045.3 7880.8) (7052.3 7880.8)) (T (7052.2 7866.8) (7045.2 7866.8) (7045.2 7868.8) (7052.2 7868.8)) (T (6971.3 7880.8) (7045.3 7880.8) (7045.2 7875.8) (6971.2 7875.8)) (nil (7045.3 7880.8) (6971.3 7880.8) (6971.3 7954.8)) (nil (6971.3 7954.8) (6990.4 7952.3) (7008.3 7944.9) (7023.6 7933.1) (7035.3 7917.8) (7042.7 7900.0) (7045.3 7880.8)) (T (3160.7 6110.7) (3163.6 6110.0) (3165.9 6119.8) (3163.0 6120.5)) (T (3156.8 6111.7) (3163.6 6110.0) (3163.1 6108.1) (3156.3 6109.7)) (T (3159.5 6123.3) (3166.4 6121.7) (3165.9 6119.8) (3159.1 6121.4)) (T (3258.0 6087.7) (3255.1 6088.4) (3257.4 6098.1) (3260.3 6097.4)) (T (3261.9 6086.8) (3255.1 6088.4) (3254.6 6086.4) (3261.4 6084.8)) (T (3264.6 6098.5) (3257.8 6100.1) (3257.4 6098.1) (3264.2 6096.5)) (T (3163.1 6108.1) (3254.6 6086.4) (3255.8 6091.3) (3164.3 6113.0)) (nil (3254.6 6086.4) (3163.1 6108.1) (3141.5 6016.6)) (nil (3254.6 6086.4) (3245.9 6063.5) (3231.5 6043.6) (3212.5 6028.1) (3190.1 6018.1) (3165.9 6014.1) (3141.5 6016.6)) (T (4808.6 7883.2) (4805.7 7882.4) (4808.1 7872.7) (4811.0 7873.5)) (T (4812.5 7884.2) (4805.7 7882.4) (4805.2 7884.4) (4812.0 7886.1)) (T (4815.4 7872.5) (4808.6 7870.8) (4808.1 7872.7) (4814.9 7874.5)) (T (4711.7 7858.5) (4714.6 7859.2) (4717.1 7849.5) (4714.2 7848.8)) (T (4707.8 7857.5) (4714.6 7859.2) (4714.1 7861.1) (4707.3 7859.4)) (T (4710.8 7845.9) (4717.6 7847.6) (4717.1 7849.5) (4710.3 7847.8)) (T (4805.2 7884.4) (4714.1 7861.1) (4715.3 7856.3) (4806.4 7879.5)) (nil (4714.1 7861.1) (4805.2 7884.4) (4782.0 7975.5)) (nil (4714.1 7861.1) (4711.2 7885.5) (4714.7 7909.8) (4724.3 7932.4) (4739.5 7951.6) (4759.2 7966.3) (4782.0 7975.5)) (T (8791.6 8677.5) (8788.6 8676.9) (8790.4 8667.1) (8793.4 8667.6)) (T (8795.5 8678.2) (8788.6 8676.9) (8788.3 8678.9) (8795.2 8680.2)) (T (8797.7 8666.4) (8790.8 8665.1) (8790.4 8667.1) (8797.3 8668.4)) (T (8693.2 8659.4) (8696.2 8659.9) (8698.0 8650.1) (8695.0 8649.5)) (T (8689.3 8658.6) (8696.2 8659.9) (8695.8 8661.9) (8688.9 8660.6)) (T (8691.5 8646.8) (8698.4 8648.1) (8698.0 8650.1) (8691.1 8648.8)) (T (8788.3 8678.9) (8695.8 8661.9) (8696.7 8657.0) (8789.2 8674.0)) (nil (8695.8 8661.9) (8788.3 8678.9) (8771.3 8771.3)) (nil (8695.8 8661.9) (8694.6 8686.4) (8699.7 8710.4) (8710.9 8732.2) (8727.3 8750.4) (8747.9 8763.8) (8771.3 8771.3)) (T (8925.0 5530.8) (8925.0 5533.8) (8915.0 5533.8) (8915.0 5530.8)) (T (8925.0 5526.8) (8925.0 5533.8) (8927.0 5533.8) (8927.0 5526.8)) (T (8913.0 5526.8) (8913.0 5533.8) (8915.0 5533.8) (8915.0 5526.8)) (T (8925.0 5630.8) (8925.0 5627.8) (8915.0 5627.8) (8915.0 5630.8)) (T (8925.0 5634.8) (8925.0 5627.8) (8927.0 5627.8) (8927.0 5634.8)) (T (8913.0 5634.8) (8913.0 5627.8) (8915.0 5627.8) (8915.0 5634.8)) (T (8927.0 5533.8) (8927.0 5627.8) (8922.0 5627.8) (8922.0 5533.8)) (nil (8927.0 5627.8) (8927.0 5533.8) (9021.0 5533.8)) (nil (8927.0 5627.8) (8951.3 5624.6) (8974.0 5615.2) (8993.5 5600.3) (9008.4 5580.8) (9017.8 5558.1) (9021.0 5533.8)) (T (7680.6 3580.0) (7678.8 3582.4) (7670.7 3576.6) (7672.4 3574.2)) (T (7682.9 3576.7) (7678.8 3582.4) (7680.4 3583.6) (7684.5 3577.9)) (T (7673.1 3569.7) (7669.1 3575.4) (7670.7 3576.6) (7674.8 3570.9)) (T (7622.2 3661.2) (7624.0 3658.8) (7615.9 3652.9) (7614.1 3655.4)) (T (7619.9 3664.5) (7624.0 3658.8) (7625.6 3659.9) (7621.5 3665.6)) (T (7610.1 3657.5) (7614.2 3651.8) (7615.9 3652.9) (7611.8 3658.6)) (T (7680.4 3583.6) (7625.6 3659.9) (7621.5 3657.0) (7676.4 3580.7)) (nil (7625.6 3659.9) (7680.4 3583.6) (7756.8 3638.4)) (nil (7625.6 3659.9) (7647.2 3671.5) (7671.1 3677.1) (7695.7 3676.4) (7719.1 3669.3) (7740.0 3656.3) (7756.8 3638.4)) (T (6178.8 5403.4) (6181.7 5402.7) (6184.0 5412.5) (6181.1 5413.1)) (T (6174.9 5404.3) (6181.7 5402.7) (6181.3 5400.8) (6174.5 5402.4)) (T (6177.7 5416.0) (6184.5 5414.4) (6184.0 5412.5) (6177.2 5414.1)) (T (6276.1 5380.4) (6273.2 5381.1) (6275.5 5390.8) (6278.4 5390.1)) (T (6280.0 5379.5) (6273.2 5381.1) (6272.7 5379.1) (6279.6 5377.5)) (T (6282.8 5391.1) (6276.0 5392.7) (6275.5 5390.8) (6282.3 5389.2)) (T (6181.3 5400.8) (6272.7 5379.1) (6273.9 5384.0) (6182.4 5405.6)) (nil (6272.7 5379.1) (6181.3 5400.8) (6159.6 5309.3)) (nil (6272.7 5379.1) (6264.0 5356.2) (6249.7 5336.3) (6230.6 5320.8) (6208.2 5310.7) (6184.0 5306.8) (6159.6 5309.3))) ((7114.2 7814.8 22.0 "BAY WC") (7114.2 7778.8 16.0 "1,5 m\\U+00B2") (7004.2 7814.8 22.0 "BAYAN WC") (7004.2 7778.8 16.0 "1,5 m\\U+00B2") (7224.5 7814.8 22.0 "\\U+00C7\\U+00D6P ODASI") (7224.5 7778.8 16.0 "2,1 m\\U+00B2") (7032.5 8286.4 22.0 "G\\U+00DCV. HOL\\U+00DC") (7032.5 8250.4 16.0 "2,1 m\\U+00B2") (7359.3 7811.9 22.0 "JENARAT\\U+00D6R ODASI") (7359.3 7775.9 16.0 "1,5 m\\U+00B2") (7190.3 8079.4 22.0 "SI\\U+011EINAK") (7190.3 8043.4 16.0 "15,5 m\\U+00B2") (7938.0 5616.7 22.0 "\\U+00DCRET\\U+0130M ALANI") (7938.0 5580.7 16.0 "1.005,3 m\\U+00B2") (4097.1 6829.4 22.0 "\\U+00DCRET\\U+0130M ALANI") (4097.1 6793.4 16.0 "1.009,7 m\\U+00B2")))
   ("T" "CLD-P2-KAK-YAZI" 97243.5 -130932.3 160.0 0 "PARSEL 2 - KUVVETL\\U+0130 AKIM - G\\U+00DC\\U+00C7 DA\\U+011EITIM PROJES\\U+0130")
   ("T" "CLD-P2-KAK-YAZI" 97243.5 -131162.3 50.0 0 "BROSCO \\U+0130THALAT \\U+0130HRACAT VE T\\U+0130CARET ANON\\U+0130M \\U+015E\\U+0130RKET\\U+0130 - YUKARI MAHALLE / KEMALPA\\U+015EA / \\U+0130ZM\\U+0130R")
   ("T" "CLD-P2-KAK-YAZI" 97243.5 -131242.3 38.0 0 "CLD otomatik proje  |  Disiplin 04  |  19.10.2026  |  Paftalar 1/100  |  Katman \\U+00F6neki CLD-P2-KAK-*")
   ("I" "CLD-P2-KAK-ALTLIK" "CLD_P2_MIMARI_ZK_V2" 97243.5 -141658.8 0.0 0.01)
   ("T" "CLD-P2-KAK-TABLO" 107325.2 -131582.3 26.0 0 "LEJANT")
   ("P" "CLD-P2-KAK-TABLO" T 0.0 ((107325.2 -131602.3) (108242.4 -131602.3) (108242.4 -132262.3) (107325.2 -132262.3)))
   ("I" "CLD-P2-KAK-TABLO" "CLD_S_ADP" 107445.2 -131644.3 0.0 0.578)
   ("T" "CLD-P2-KAK-TABLO" 107565.2 -131644.3 20.0 7 "Ana da\\U+011F\\U+0131t\\U+0131m panosu (ADP) - kompakt \\U+015Falter, \\U+00F6l\\U+00E7\\U+00FC, SPD")
   ("I" "CLD-P2-KAK-TABLO" "CLD_S_TP" 107445.2 -131708.3 0.0 1.04)
   ("T" "CLD-P2-KAK-TABLO" 107565.2 -131708.3 20.0 7 "Tali da\\U+011F\\U+0131t\\U+0131m panosu")
   ("I" "CLD-P2-KAK-TABLO" "CLD_S_KMP" 107445.2 -131772.3 0.0 0.867)
   ("T" "CLD-P2-KAK-TABLO" 107565.2 -131772.3 20.0 7 "Kompanzasyon panosu (otomatik, harmonik filtreli)")
   ("I" "CLD-P2-KAK-TABLO" "CLD_S_OAP" 107445.2 -131836.3 0.0 0.867)
   ("T" "CLD-P2-KAK-TABLO" 107565.2 -131836.3 20.0 7 "Mekanik / yang\\U+0131n pompa panosu")
   ("I" "CLD-P2-KAK-TABLO" "CLD_S_KOLON" 107445.2 -131900.3 0.0 1.733)
   ("T" "CLD-P2-KAK-TABLO" 107565.2 -131900.3 20.0 7 "Kat kolon (dikey besleme) ge\\U+00E7i\\U+015Fi")
   ("I" "CLD-P2-KAK-TABLO" "CLD_S_TRAFO" 107445.2 -131964.3 0.0 0.087)
   ("T" "CLD-P2-KAK-TABLO" 107565.2 -131964.3 20.0 7 "K\\U+00F6\\U+015Fk tipi trafo merkezi")
   ("I" "CLD-P2-KAK-TABLO" "CLD_S_JEN" 107445.2 -132028.3 0.0 0.13)
   ("T" "CLD-P2-KAK-TABLO" 107565.2 -132028.3 20.0 7 "Dizel jenerat\\U+00F6r grubu + otomatik transfer")
   ("I" "CLD-P2-KAK-TABLO" "CLD_S_PRJ" 107445.2 -132092.3 0.0 1.182)
   ("T" "CLD-P2-KAK-TABLO" 107565.2 -132092.3 20.0 7 "LED projekt\\U+00F6r 100 W, 12.000 lm, IP66 (cephe)")
   ("P" "CLD-P2-KAK-BESLEME" nil 0.0 ((107345.2 -132156.3) (107545.2 -132156.3)))
   ("T" "CLD-P2-KAK-TABLO" 107565.2 -132156.3 20.0 7 "Besleme kablosu g\\U+00FCzergah\\U+0131 (kablo tavas\\U+0131, NYY / FE180)")
   ("P" "CLD-P2-KAK-BARA" nil 0.0 ((107345.2 -132220.3) (107545.2 -132220.3)))
   ("T" "CLD-P2-KAK-TABLO" 107565.2 -132220.3 20.0 7 "Makine besleme bara kanal\\U+0131 (busbar) 3P+N+PE")
   ("P" "CLD-P2-KAK-PAFTA" nil 6.0 ((107175.2 -141678.8) (107175.2 -131432.3)))
   ("P" "CLD-P2-KAK-PAFTA" T 10.0 ((97143.5 -142358.8) (108492.4 -142358.8) (108492.4 -131432.3) (97143.5 -131432.3)))
   ("P" "CLD-P2-KAK-PAFTA" nil 6.0 ((97143.5 -141678.8) (108492.4 -141678.8)))
   ("P" "CLD-P2-KAK-PAFTA" T 6.0 ((105992.4 -142358.8) (108492.4 -142358.8) (108492.4 -141678.8) (105992.4 -141678.8)))
   ("T" "CLD-P2-KAK-YAZI" 106022.4 -141742.0 18.0 0 "\\U+0130\\U+015E\\U+0130N ADI")
   ("T" "CLD-P2-KAK-YAZI" 106612.4 -141742.0 20.0 0 "KUVVETL\\U+0130 AKIM - G\\U+00DC\\U+00C7 DA\\U+011EITIM PROJES\\U+0130")
   ("L" "CLD-P2-KAK-PAFTA" 105992.4 -141776.0 108492.4 -141776.0)
   ("T" "CLD-P2-KAK-YAZI" 106022.4 -141839.1 18.0 0 "YAPI SAH\\U+0130B\\U+0130")
   ("T" "CLD-P2-KAK-YAZI" 106612.4 -141839.1 20.0 0 "BROSCO \\U+0130THALAT \\U+0130HRACAT VE T\\U+0130CARET ANON\\U+0130M \\U+015E\\U+0130RKET\\U+0130")
   ("L" "CLD-P2-KAK-PAFTA" 105992.4 -141873.1 108492.4 -141873.1)
   ("T" "CLD-P2-KAK-YAZI" 106022.4 -141936.3 18.0 0 "ADRES")
   ("T" "CLD-P2-KAK-YAZI" 106612.4 -141936.3 20.0 0 "YUKARI MAHALLE / KEMALPA\\U+015EA / \\U+0130ZM\\U+0130R  -  Ada: ......  Parsel: 2")
   ("L" "CLD-P2-KAK-PAFTA" 105992.4 -141970.3 108492.4 -141970.3)
   ("T" "CLD-P2-KAK-YAZI" 106022.4 -142033.4 18.0 0 "PAFTA ADI")
   ("T" "CLD-P2-KAK-YAZI" 106612.4 -142033.4 20.0 0 "G\\U+00DC\\U+00C7 DA\\U+011EITIM PLANI (pano, besleme hatt\\U+0131, bara kan - ZEM\\U+0130N KAT PLANI")
   ("L" "CLD-P2-KAK-PAFTA" 105992.4 -142067.4 108492.4 -142067.4)
   ("T" "CLD-P2-KAK-YAZI" 106022.4 -142130.5 18.0 0 "\\U+00D6L\\U+00C7EK / TAR\\U+0130H / PAFTA NO")
   ("T" "CLD-P2-KAK-YAZI" 106612.4 -142130.5 20.0 0 "1/100   |   19.10.2026   |   04-01")
   ("L" "CLD-P2-KAK-PAFTA" 105992.4 -142164.5 108492.4 -142164.5)
   ("T" "CLD-P2-KAK-YAZI" 106022.4 -142227.7 18.0 0 "PROJE M\\U+00DCELL\\U+0130F\\U+0130")
   ("T" "CLD-P2-KAK-YAZI" 106612.4 -142227.7 20.0 0 "Elektrik M\\U+00FChendisi - Ad\\U+0131 Soyad\\U+0131: ..............................")
   ("L" "CLD-P2-KAK-PAFTA" 105992.4 -142261.7 108492.4 -142261.7)
   ("T" "CLD-P2-KAK-YAZI" 106022.4 -142324.8 18.0 0 "ODA S\\U+0130C\\U+0130L / SMM NO")
   ("T" "CLD-P2-KAK-YAZI" 106612.4 -142324.8 20.0 0 "EMO Sicil No: ............   SMM Belge No: ............   \\U+0130mza: ............")
   ("L" "CLD-P2-KAK-PAFTA" 106582.4 -142358.8 106582.4 -141678.8)
   ("T" "CLD-P2-KAK-YAZI" 97243.5 -141818.8 70.0 0 "G\\U+00DC\\U+00C7 DA\\U+011EITIM PLANI (pano, besleme hatt\\U+0131, bara kanal\\U+0131)")
   ("T" "CLD-P2-KAK-YAZI" 97243.5 -141958.8 40.0 0 "ZEM\\U+0130N KAT PLANI  -  \\U+00D6: 1/100")
   ("T" "CLD-P2-KAK-YAZI" 97243.5 -142058.8 30.0 0 "Parsel 2  |  BROSCO \\U+0130THALAT \\U+0130HRACAT VE T\\U+0130CARET ANON\\U+0130M \\U+015E\\U+0130RKET\\U+0130")
   ("T" "CLD-P2-KAK-YAZI" 97243.5 -142138.8 26.0 0 "CLD - 19.10.2026 - mimari altl\\U+0131k: BROSCO 2 NOLU PARSEL M\\U+0130MAR\\U+0130.dwg")
   ("I" "CLD-P2-KAK-PANO" "CLD_S_ADP" 104885.2 -133270.1 0.0 2.5)
   ("T" "CLD-P2-KAK-PANO" 104945.2 -133210.1 30.0 0 "ADP")
   ("I" "CLD-P2-KAK-PANO" "CLD_S_KMP" 104885.2 -133410.1 0.0 2.5)
   ("T" "CLD-P2-KAK-PANO" 104945.2 -133350.1 30.0 0 "KMP")
   ("I" "CLD-P2-KAK-PANO" "CLD_S_OAP" 104885.2 -133130.1 0.0 2.5)
   ("T" "CLD-P2-KAK-PANO" 104945.2 -133070.1 30.0 0 "MKP")
   ("P" "CLD-P2-KAK-BESLEME" nil 6.0 ((104885.2 -133270.1) (104885.2 -133130.1)))
   ("T" "CLD-P2-KAK-YAZI" 104915.2 -133100.1 18.0 0 "MKP: NYY 5x6 mm\\U+00B2")
   ("I" "CLD-P2-KAK-PANO" "CLD_S_OAP" 103815.3 -132772.3 0.0 2.5)
   ("T" "CLD-P2-KAK-PANO" 103875.3 -132712.3 30.0 0 "YPP")
   ("P" "CLD-P2-KAK-BESLEME" nil 6.0 ((104761.8 -132609.1) (103815.3 -132772.3)))
   ("T" "CLD-P2-KAK-YAZI" 103845.3 -132742.3 18.0 0 "YPP: NHXH-FE180/E90 5x10 mm\\U+00B2")
   ("I" "CLD-P2-KAK-PANO" "CLD_S_TP" 101843.0 -135841.7 1.3406 2.5)
   ("T" "CLD-P2-KAK-PANO" 101903.0 -135781.7 30.0 0 "UTP-1")
   ("P" "CLD-P2-KAK-BESLEME" nil 6.0 ((104885.2 -133270.1) (101843.0 -133270.1) (101843.0 -135841.7)))
   ("T" "CLD-P2-KAK-YAZI" 101873.0 -133240.1 18.0 0 "UTP-1: NYY 3x25+16 + 1x16 (PE) mm\\U+00B2")
   ("I" "CLD-P2-KAK-PANO" "CLD_S_TP" 106125.8 -135954.5 3.1415 2.5)
   ("T" "CLD-P2-KAK-PANO" 106185.8 -135894.5 30.0 0 "UTP-2")
   ("P" "CLD-P2-KAK-BESLEME" nil 6.0 ((104885.2 -133270.1) (104885.2 -135954.5) (106125.8 -135954.5)))
   ("T" "CLD-P2-KAK-YAZI" 104915.2 -135924.5 18.0 0 "UTP-2: NYY 3x25+16 + 1x16 (PE) mm\\U+00B2")
   ("I" "CLD-P2-KAK-PANO" "CLD_S_TP" 104377.4 -133484.5 3.1416 2.5)
   ("T" "CLD-P2-KAK-PANO" 104437.4 -133424.5 30.0 0 "IDP-ZK")
   ("P" "CLD-P2-KAK-BESLEME" nil 6.0 ((104885.2 -133270.1) (104377.4 -133270.1) (104377.4 -133484.5)))
   ("T" "CLD-P2-KAK-YAZI" 104407.4 -133240.1 18.0 0 "IDP-ZK: NYY 5x10 mm\\U+00B2")
   ("P" "CLD-P2-KAK-BESLEME" nil 6.0 ((104885.2 -133270.1) (104882.9 -133257.9) (104384.9 -133350.9) (104425.5 -133568.2)))
   ("T" "CLD-P2-KAK-YAZI" 104414.9 -133320.9 18.0 0 "IDP-1K: NYY 5x10 mm\\U+00B2")
   ("I" "CLD-P2-KAK-PANO" "CLD_S_KOLON" 104425.5 -133568.2 0.0 2.5)
   ("T" "CLD-P2-KAK-YAZI" 104475.5 -133628.2 18.0 0 "IDP-1K kolon \\U+00E7\\U+0131k\\U+0131\\U+015F\\U+0131 (+3,00)")
   ("P" "CLD-P2-KAK-BARA" nil 15.0 ((102786.2 -135127.4) (101455.4 -135375.9)))
   ("T" "CLD-P2-KAK-YAZI" 102836.2 -135067.4 25.0 0 "BARA-1: Makine besleme bara kanal\\U+0131 160 A (3P+N+PE)")
   ("P" "CLD-P2-KAK-BESLEME" nil 6.0 ((104885.2 -133270.1) (104882.9 -133257.9) (104268.9 -133372.6) (104265.5 -133373.1) (104178.6 -133384.1) (104129.1 -133398.4) (104123.5 -133399.7) (102791.4 -133649.0) (98472.1 -134750.4) (98809.5 -135081.0) (98910.5 -135136.4) (102582.4 -135996.9) (102786.2 -135127.4)))
   ("T" "CLD-P2-KAK-YAZI" 102836.2 -135217.4 18.0 0 "besleme NYY 3x120+70 + 1x70 (PE) mm\\U+00B2")
   ("P" "CLD-P2-KAK-BARA" nil 15.0 ((104947.3 -137423.7) (104947.3 -135910.4)))
   ("T" "CLD-P2-KAK-YAZI" 104997.3 -137363.7 25.0 0 "BARA-2: Makine besleme bara kanal\\U+0131 160 A (3P+N+PE)")
   ("P" "CLD-P2-KAK-BESLEME" nil 6.0 ((104885.2 -133270.1) (104882.9 -133257.9) (106108.5 -133029.1) (106108.1 -139646.7) (104664.5 -137625.6) (104947.3 -137423.7)))
   ("T" "CLD-P2-KAK-YAZI" 104997.3 -137513.7 18.0 0 "besleme NYY 3x120+70 + 1x70 (PE) mm\\U+00B2")
   ("I" "CLD-P2-KAK-TRAFO-JEN" "CLD_S_TRAFO" 104761.8 -132609.1 0.0 1.0)
   ("T" "CLD-P2-KAK-TRAFO-JEN" 105111.8 -132609.1 30.0 7 "K\\U+00D6\\U+015EK T\\U+0130P\\U+0130 TRAFO 34,5/0,4 kV 250 kVA")
   ("I" "CLD-P2-KAK-TRAFO-JEN" "CLD_S_JEN" 105548.2 -132462.3 0.0 1.0)
   ("T" "CLD-P2-KAK-TRAFO-JEN" 105798.2 -132462.3 30.0 7 "D\\U+0130ZEL JENERAT\\U+00D6R 45 kVA + ATS")
   ("P" "CLD-P2-KAK-BESLEME" nil 10.0 ((104761.8 -132609.1) (104885.2 -133270.1)))
   ("T" "CLD-P2-KAK-YAZI" 104853.5 -132909.6 18.0 0 "trafo-ADP: 2 x (NYY 3x185+95 + 1x95 PE) mm\\U+00B2 - her hatta ayr\\U+0131 PE")
   ("P" "CLD-P2-KAK-BESLEME" nil 10.0 ((105548.2 -132462.3) (104885.2 -133270.1)))
   ("P" "CLD-P2-KAK-BESLEME" nil 6.0 ((105548.2 -132462.3) (103815.3 -132462.3) (103815.3 -132772.3)))
   ("T" "CLD-P2-KAK-YAZI" 103845.3 -132552.3 18.0 0 "JEN-YPP yedek besleme: NHXH-FE180/E90 5x10 mm\\U+00B2")
   ("I" "CLD-P2-KAK-CEPHE-AYD" "CLD_S_PRJ" 99212.7 -134499.7 0.0 2.5)
   ("I" "CLD-P2-KAK-CEPHE-AYD" "CLD_S_PRJ" 100930.2 -134061.7 0.0 2.5)
   ("I" "CLD-P2-KAK-CEPHE-AYD" "CLD_S_PRJ" 102647.8 -133623.7 0.0 2.5)
   ("I" "CLD-P2-KAK-CEPHE-AYD" "CLD_S_PRJ" 104387.8 -133289.3 0.0 2.5)
   ("I" "CLD-P2-KAK-CEPHE-AYD" "CLD_S_PRJ" 106130.2 -132964.0 0.0 2.5)
   ("I" "CLD-P2-KAK-CEPHE-AYD" "CLD_S_PRJ" 106168.4 -134690.4 0.0 2.5)
   ("I" "CLD-P2-KAK-CEPHE-AYD" "CLD_S_PRJ" 106168.3 -136462.9 0.0 2.5)
   ("I" "CLD-P2-KAK-CEPHE-AYD" "CLD_S_PRJ" 106168.2 -138235.5 0.0 2.5)
   ("I" "CLD-P2-KAK-CEPHE-AYD" "CLD_S_PRJ" 106066.9 -139692.3 0.0 2.5)
   ("I" "CLD-P2-KAK-CEPHE-AYD" "CLD_S_PRJ" 105036.7 -138249.9 0.0 2.5)
   ("I" "CLD-P2-KAK-CEPHE-AYD" "CLD_S_PRJ" 104006.4 -136807.6 0.0 2.5)
   ("I" "CLD-P2-KAK-CEPHE-AYD" "CLD_S_PRJ" 102503.3 -136040.0 0.0 2.5)
   ("I" "CLD-P2-KAK-CEPHE-AYD" "CLD_S_PRJ" 100777.5 -135635.6 0.0 2.5)
   ("I" "CLD-P2-KAK-CEPHE-AYD" "CLD_S_PRJ" 99051.8 -135231.1 0.0 2.5)
   ("I" "CLD-P2-KAK-ALTLIK" "CLD_P2_MIMARI_1K_V2" 109592.4 -141658.8 0.0 0.01)
   ("T" "CLD-P2-KAK-TABLO" 119513.3 -131582.3 26.0 0 "LEJANT")
   ("P" "CLD-P2-KAK-TABLO" T 0.0 ((119513.3 -131602.3) (120430.5 -131602.3) (120430.5 -132262.3) (119513.3 -132262.3)))
   ("I" "CLD-P2-KAK-TABLO" "CLD_S_ADP" 119633.3 -131644.3 0.0 0.578)))))
(defun cld:ops-p2_kuvvetli_akim-2 () (cld:play (quote (
   ("T" "CLD-P2-KAK-TABLO" 119753.3 -131644.3 20.0 7 "Ana da\\U+011F\\U+0131t\\U+0131m panosu (ADP) - kompakt \\U+015Falter, \\U+00F6l\\U+00E7\\U+00FC, SPD")
   ("I" "CLD-P2-KAK-TABLO" "CLD_S_TP" 119633.3 -131708.3 0.0 1.04)
   ("T" "CLD-P2-KAK-TABLO" 119753.3 -131708.3 20.0 7 "Tali da\\U+011F\\U+0131t\\U+0131m panosu")
   ("I" "CLD-P2-KAK-TABLO" "CLD_S_KMP" 119633.3 -131772.3 0.0 0.867)
   ("T" "CLD-P2-KAK-TABLO" 119753.3 -131772.3 20.0 7 "Kompanzasyon panosu (otomatik, harmonik filtreli)")
   ("I" "CLD-P2-KAK-TABLO" "CLD_S_OAP" 119633.3 -131836.3 0.0 0.867)
   ("T" "CLD-P2-KAK-TABLO" 119753.3 -131836.3 20.0 7 "Mekanik / yang\\U+0131n pompa panosu")
   ("I" "CLD-P2-KAK-TABLO" "CLD_S_KOLON" 119633.3 -131900.3 0.0 1.733)
   ("T" "CLD-P2-KAK-TABLO" 119753.3 -131900.3 20.0 7 "Kat kolon (dikey besleme) ge\\U+00E7i\\U+015Fi")
   ("I" "CLD-P2-KAK-TABLO" "CLD_S_TRAFO" 119633.3 -131964.3 0.0 0.087)
   ("T" "CLD-P2-KAK-TABLO" 119753.3 -131964.3 20.0 7 "K\\U+00F6\\U+015Fk tipi trafo merkezi")
   ("I" "CLD-P2-KAK-TABLO" "CLD_S_JEN" 119633.3 -132028.3 0.0 0.13)
   ("T" "CLD-P2-KAK-TABLO" 119753.3 -132028.3 20.0 7 "Dizel jenerat\\U+00F6r grubu + otomatik transfer")
   ("I" "CLD-P2-KAK-TABLO" "CLD_S_PRJ" 119633.3 -132092.3 0.0 1.182)
   ("T" "CLD-P2-KAK-TABLO" 119753.3 -132092.3 20.0 7 "LED projekt\\U+00F6r 100 W, 12.000 lm, IP66 (cephe)")
   ("P" "CLD-P2-KAK-BESLEME" nil 0.0 ((119533.3 -132156.3) (119733.3 -132156.3)))
   ("T" "CLD-P2-KAK-TABLO" 119753.3 -132156.3 20.0 7 "Besleme kablosu g\\U+00FCzergah\\U+0131 (kablo tavas\\U+0131, NYY / FE180)")
   ("P" "CLD-P2-KAK-BARA" nil 0.0 ((119533.3 -132220.3) (119733.3 -132220.3)))
   ("T" "CLD-P2-KAK-TABLO" 119753.3 -132220.3 20.0 7 "Makine besleme bara kanal\\U+0131 (busbar) 3P+N+PE")
   ("P" "CLD-P2-KAK-PAFTA" nil 6.0 ((119363.3 -141678.8) (119363.3 -131432.3)))
   ("P" "CLD-P2-KAK-PAFTA" T 10.0 ((109492.4 -142358.8) (120680.5 -142358.8) (120680.5 -131432.3) (109492.4 -131432.3)))
   ("P" "CLD-P2-KAK-PAFTA" nil 6.0 ((109492.4 -141678.8) (120680.5 -141678.8)))
   ("P" "CLD-P2-KAK-PAFTA" T 6.0 ((118180.5 -142358.8) (120680.5 -142358.8) (120680.5 -141678.8) (118180.5 -141678.8)))
   ("T" "CLD-P2-KAK-YAZI" 118210.5 -141742.0 18.0 0 "\\U+0130\\U+015E\\U+0130N ADI")
   ("T" "CLD-P2-KAK-YAZI" 118800.5 -141742.0 20.0 0 "KUVVETL\\U+0130 AKIM - G\\U+00DC\\U+00C7 DA\\U+011EITIM PROJES\\U+0130")
   ("L" "CLD-P2-KAK-PAFTA" 118180.5 -141776.0 120680.5 -141776.0)
   ("T" "CLD-P2-KAK-YAZI" 118210.5 -141839.1 18.0 0 "YAPI SAH\\U+0130B\\U+0130")
   ("T" "CLD-P2-KAK-YAZI" 118800.5 -141839.1 20.0 0 "BROSCO \\U+0130THALAT \\U+0130HRACAT VE T\\U+0130CARET ANON\\U+0130M \\U+015E\\U+0130RKET\\U+0130")
   ("L" "CLD-P2-KAK-PAFTA" 118180.5 -141873.1 120680.5 -141873.1)
   ("T" "CLD-P2-KAK-YAZI" 118210.5 -141936.3 18.0 0 "ADRES")
   ("T" "CLD-P2-KAK-YAZI" 118800.5 -141936.3 20.0 0 "YUKARI MAHALLE / KEMALPA\\U+015EA / \\U+0130ZM\\U+0130R  -  Ada: ......  Parsel: 2")
   ("L" "CLD-P2-KAK-PAFTA" 118180.5 -141970.3 120680.5 -141970.3)
   ("T" "CLD-P2-KAK-YAZI" 118210.5 -142033.4 18.0 0 "PAFTA ADI")
   ("T" "CLD-P2-KAK-YAZI" 118800.5 -142033.4 20.0 0 "G\\U+00DC\\U+00C7 DA\\U+011EITIM PLANI (pano, besleme hatt\\U+0131, bara kan - 1. KAT PLANI")
   ("L" "CLD-P2-KAK-PAFTA" 118180.5 -142067.4 120680.5 -142067.4)
   ("T" "CLD-P2-KAK-YAZI" 118210.5 -142130.5 18.0 0 "\\U+00D6L\\U+00C7EK / TAR\\U+0130H / PAFTA NO")
   ("T" "CLD-P2-KAK-YAZI" 118800.5 -142130.5 20.0 0 "1/100   |   19.10.2026   |   04-02")
   ("L" "CLD-P2-KAK-PAFTA" 118180.5 -142164.5 120680.5 -142164.5)
   ("T" "CLD-P2-KAK-YAZI" 118210.5 -142227.7 18.0 0 "PROJE M\\U+00DCELL\\U+0130F\\U+0130")
   ("T" "CLD-P2-KAK-YAZI" 118800.5 -142227.7 20.0 0 "Elektrik M\\U+00FChendisi - Ad\\U+0131 Soyad\\U+0131: ..............................")
   ("L" "CLD-P2-KAK-PAFTA" 118180.5 -142261.7 120680.5 -142261.7)
   ("T" "CLD-P2-KAK-YAZI" 118210.5 -142324.8 18.0 0 "ODA S\\U+0130C\\U+0130L / SMM NO")
   ("T" "CLD-P2-KAK-YAZI" 118800.5 -142324.8 20.0 0 "EMO Sicil No: ............   SMM Belge No: ............   \\U+0130mza: ............")
   ("L" "CLD-P2-KAK-PAFTA" 118770.5 -142358.8 118770.5 -141678.8)
   ("T" "CLD-P2-KAK-YAZI" 109592.4 -141818.8 70.0 0 "G\\U+00DC\\U+00C7 DA\\U+011EITIM PLANI (pano, besleme hatt\\U+0131, bara kanal\\U+0131)")
   ("T" "CLD-P2-KAK-YAZI" 109592.4 -141958.8 40.0 0 "1. KAT PLANI  -  \\U+00D6: 1/100")
   ("T" "CLD-P2-KAK-YAZI" 109592.4 -142058.8 30.0 0 "Parsel 2  |  BROSCO \\U+0130THALAT \\U+0130HRACAT VE T\\U+0130CARET ANON\\U+0130M \\U+015E\\U+0130RKET\\U+0130")
   ("T" "CLD-P2-KAK-YAZI" 109592.4 -142138.8 26.0 0 "CLD - 19.10.2026 - mimari altl\\U+0131k: BROSCO 2 NOLU PARSEL M\\U+0130MAR\\U+0130.dwg")
   ("I" "CLD-P2-KAK-PANO" "CLD_S_TP" 116709.0 -133572.1 1.5711 2.5)
   ("T" "CLD-P2-KAK-PANO" 116769.0 -133512.1 30.0 0 "IDP-1K")
   ("I" "CLD-P2-KAK-PANO" "CLD_S_KOLON" 116709.0 -133472.1 0.0 2.5)
   ("P" "CLD-P2-KAK-BESLEME" nil 6.0 ((116709.0 -133472.1) (116709.0 -133572.1)))
   ("T" "CLD-P2-KAK-YAZI" 116759.0 -133532.1 18.0 0 "IDP-1K kolon giri\\U+015Fi - NYY 5x10 mm\\U+00B2")
   ("T" "CLD-P2-KAK-TABLO" 121780.5 -131682.3 32.5 0 "LEJANT")
   ("P" "CLD-P2-KAK-TABLO" T 0.0 ((121780.5 -131707.3) (122927.0 -131707.3) (122927.0 -132532.3) (121780.5 -132532.3)))
   ("I" "CLD-P2-KAK-TABLO" "CLD_S_ADP" 121930.5 -131759.8 0.0 0.722)
   ("T" "CLD-P2-KAK-TABLO" 122080.5 -131759.8 25.0 7 "Ana da\\U+011F\\U+0131t\\U+0131m panosu (ADP) - kompakt \\U+015Falter, \\U+00F6l\\U+00E7\\U+00FC, SPD")
   ("I" "CLD-P2-KAK-TABLO" "CLD_S_TP" 121930.5 -131839.8 0.0 1.3)
   ("T" "CLD-P2-KAK-TABLO" 122080.5 -131839.8 25.0 7 "Tali da\\U+011F\\U+0131t\\U+0131m panosu")
   ("I" "CLD-P2-KAK-TABLO" "CLD_S_KMP" 121930.5 -131919.8 0.0 1.083)
   ("T" "CLD-P2-KAK-TABLO" 122080.5 -131919.8 25.0 7 "Kompanzasyon panosu (otomatik, harmonik filtreli)")
   ("I" "CLD-P2-KAK-TABLO" "CLD_S_OAP" 121930.5 -131999.8 0.0 1.083)
   ("T" "CLD-P2-KAK-TABLO" 122080.5 -131999.8 25.0 7 "Mekanik / yang\\U+0131n pompa panosu")
   ("I" "CLD-P2-KAK-TABLO" "CLD_S_KOLON" 121930.5 -132079.8 0.0 2.167)
   ("T" "CLD-P2-KAK-TABLO" 122080.5 -132079.8 25.0 7 "Kat kolon (dikey besleme) ge\\U+00E7i\\U+015Fi")
   ("I" "CLD-P2-KAK-TABLO" "CLD_S_TRAFO" 121930.5 -132159.8 0.0 0.108)
   ("T" "CLD-P2-KAK-TABLO" 122080.5 -132159.8 25.0 7 "K\\U+00F6\\U+015Fk tipi trafo merkezi")
   ("I" "CLD-P2-KAK-TABLO" "CLD_S_JEN" 121930.5 -132239.8 0.0 0.163)
   ("T" "CLD-P2-KAK-TABLO" 122080.5 -132239.8 25.0 7 "Dizel jenerat\\U+00F6r grubu + otomatik transfer")
   ("I" "CLD-P2-KAK-TABLO" "CLD_S_PRJ" 121930.5 -132319.8 0.0 1.477)
   ("T" "CLD-P2-KAK-TABLO" 122080.5 -132319.8 25.0 7 "LED projekt\\U+00F6r 100 W, 12.000 lm, IP66 (cephe)")
   ("P" "CLD-P2-KAK-BESLEME" nil 0.0 ((121805.5 -132399.8) (122055.5 -132399.8)))
   ("T" "CLD-P2-KAK-TABLO" 122080.5 -132399.8 25.0 7 "Besleme kablosu g\\U+00FCzergah\\U+0131 (kablo tavas\\U+0131, NYY / FE180)")
   ("P" "CLD-P2-KAK-BARA" nil 0.0 ((121805.5 -132479.8) (122055.5 -132479.8)))
   ("T" "CLD-P2-KAK-TABLO" 122080.5 -132479.8 25.0 7 "Makine besleme bara kanal\\U+0131 (busbar) 3P+N+PE")
   ("TB" "CLD-P2-KAK-TABLO" 123327.0 -131682.3 25.0 "BESLEME HATLARI - KABLO VE GER\\U+0130L\\U+0130M D\\U+00DC\\U+015E\\U+00DCM\\U+00DC HESABI" (("PANO" "BESLEME" "KURULU (kW)" "TALEP (kW)" "I (A)" "KORUMA" "KABLO" "L (m)" "%e" "Ik3 (kA)") ("ADP" "TRAFO" "238,61" "148,46" "238,1" "400 A kompakt + toroid KAKR" "2 x (NYY 3x185+95 + 1x95 PE) mm\\U+00B2 - her hatta ayr\\U+0131 PE" "14,7" "0,07" "9,3") ("MKP" "ADP" "13,75" "11,00" "17,6" "25 A + B tipi 300 mA S" "NYY 5x6 mm\\U+00B2" "6,5" "0,13" "7,2") ("YPP" "TRAFO (ana \\U+015Falter \\U+00F6ncesi) - normal" "6,60" "6,60" "10,6" "aM sigorta 32 A (ana \\U+015Falter \\U+00F6ncesi), KAKR yok (yaln\\U+0131z alarm)" "NHXH-FE180/E90 5x10 mm\\U+00B2" "15,6" "0,11" "6,3") ("YPP" "JENERAT\\U+00D6R (ATS \\U+00F6ncesi) - yedek" "6,60" "6,60" "11,2" "aM sigorta 32 A, TS-YP" "NHXH-FE180/E90 5x10 mm\\U+00B2" "27,5" "0,20" "-") ("UTP-1" "ADP" "41,06" "26,22" "42,0" "63 A + 300 mA S" "NYY 3x25+16 + 1x16 (PE) mm\\U+00B2" "66,8" "0,78" "4,2") ("UTP-2" "ADP" "41,21" "26,35" "42,3" "63 A + 300 mA S" "NYY 3x25+16 + 1x16 (PE) mm\\U+00B2" "48,2" "0,57" "5,2") ("IDP-ZK" "ADP" "4,45" "3,56" "5,7" "32 A + 300 mA S" "NYY 5x10 mm\\U+00B2" "12,9" "0,05" "6,7") ("IDP-1K" "ADP" "9,24" "7,39" "11,9" "40 A + 300 mA S" "NYY 5x10 mm\\U+00B2" "17,1" "0,14" "5,8") ("BARA-1" "ADP" "60,58" "36,35" "61,7" "160 A + 1 A S (ayarl\\U+0131 toroid)" "NYY 3x120+70 + 1x70 (PE) mm\\U+00B2" "136,4" "0,46" "5,7") ("BARA-2" "ADP" "60,32" "36,19" "61,5" "160 A + 1 A S (ayarl\\U+0131 toroid)" "NYY 3x120+70 + 1x70 (PE) mm\\U+00B2" "123,8" "0,42" "5,9") ("CEPHE AYD." "ADP" "1,40" "1,40" "2,2" "16 A + 300 mA, fotosel" "NYY 5x2,5 mm\\U+00B2" "136,0" "0,85" "-")))
   ("TB" "CLD-P2-KAK-TABLO" 123327.0 -132657.3 25.0 "G\\U+00DC\\U+00C7, TRAFO, KOMPANZASYON VE JENERAT\\U+00D6R SE\\U+00C7\\U+0130M\\U+0130" (("B\\U+00DCY\\U+00DCKL\\U+00DCK" "DE\\U+011EER" "A\\U+00C7IKLAMA") ("Toplam kurulu g\\U+00FC\\U+00E7" "238,61 kW" "T\\U+00FCm panolar + bara kanallar\\U+0131 + cephe + yang\\U+0131n pompas\\U+0131") ("Makine y\\U+00FCk yo\\U+011Funlu\\U+011Fu (kabul)" "60 W/m\\U+00B2" "Hafif imalat / montaj (makine listesi gelince g\\U+00FCncellenecek)") ("Toplam talep g\\U+00FCc\\U+00FC" "148,46 kW" "E\\U+015Fzamanl\\U+0131l\\U+0131k: makine 0,6 - ayd\\U+0131nlatma 0,9 - priz 0,6 - ofis 0,8; yang\\U+0131n pompas\\U+0131 hari\\U+00E7") ("Gerekli g\\U+00F6r\\U+00FCn\\U+00FCr g\\U+00FC\\U+00E7" "187,5 kVA" "cos\\U+03C6=0,95 (kompanzasyon sonras\\U+0131), %20 rezerv") ("Trafo" "250 kVA, 34,5/0,4 kV, Dyn11, uk=%4" "K\\U+00F6\\U+015Fk tipi, OSB OG \\U+015Febekesinden") ("Trafo sekonder ak\\U+0131m\\U+0131" "360,8 A" "ADP ana \\U+015Falteri 400 A kompakt \\U+015Falter") ("Trafo - ADP kablosu" "2 x (NYY 3x185+95 + 1x95 PE) mm\\U+00B2 - her hatta ayr\\U+0131 PE" "Iz\\U+00B7k = 426 A \\U+2265 400 A (paralel ve tava katsay\\U+0131lar\\U+0131 dahil)") ("ADP k\\U+0131sa devre ak\\U+0131m\\U+0131" "9,3 kA (sonsuz \\U+015Febeke: 9,0 kA)" "Ik3 = c\\U+00B7Un/(\\U+221A3\\U+00B7Z), c=1,05; ADP \\U+015Falterleri Icu \\U+2265 25 kA, tali panolar tabloda Ik3 de\\U+011Ferinin \\U+00FCzerinde (\\U+2265 10 kA)") ("Ka\\U+00E7ak ak\\U+0131m korumas\\U+0131" "ADP: toroid KAKR 0,3-3 A ayarl\\U+0131" "Tali pano giri\\U+015Fleri 300 mA S (se\\U+00E7ici), son devreler 30 mA (priz, ayd\\U+0131nlatma, \\U+0131slak hacim), 3 faz motor 300 mA; yang\\U+0131n pompas\\U+0131 beslemesinde KAKR yok (yaln\\U+0131z alarm)") ("Kompanzasyon g\\U+00FCc\\U+00FC" "81,2 kVAr \\U+2192 90 kVAr" "cos\\U+03C6 0,80 \\U+2192 0,98, reaktif r\\U+00F6lesi + harmonik filtre") ("Acil (jenerat\\U+00F6r) y\\U+00FCkleri" "17,56 kW" "\\U+0130dari b\\U+00F6l\\U+00FCm panolar\\U+0131 10,96 kW + yang\\U+0131n pompas\\U+0131 6,60 kW") ("Jenerat\\U+00F6r \\U+00E7al\\U+0131\\U+015Fma g\\U+00FCc\\U+00FC" "27,4 kVA" "cos\\U+03C6 0,8, %25 rezerv") ("Pompa yol alma kontrol\\U+00FC" "35,8 kVA" "idari y\\U+00FCk + yang\\U+0131n pompas\\U+0131 yumu\\U+015Fak yol verici ile (~3 x In \\U+2248 22,1 kVA)") ("Jenerat\\U+00F6r" "45 kVA dizel, ATS" "\\U+0130ki \\U+015Fart\\U+0131n b\\U+00FCy\\U+00FC\\U+011F\\U+00FCne g\\U+00F6re standart g\\U+00FC\\U+00E7")))
   ("NT" "CLD-P2-KAK-TABLO" 123327.0 -133782.3 25.0 "NOTLAR" ("1- Hesaplar Elektrik \\U+0130\\U+00E7 Tesisleri Y\\U+00F6netmeli\\U+011Fi ve TS HD 60364 e g\\U+00F6redir. Besleme hatlar\\U+0131nda gerilim d\\U+00FC\\U+015F\\U+00FCm\\U+00FC \\U+2264 %1,5." "2- Kesitler IEC 60364-5-52 C y\\U+00F6ntemi de\\U+011Ferleri x 0,71 (tava gruplama 0,82 x 40 \\U+00B0C ortam 0,87) ile se\\U+00E7ilmi\\U+015Ftir." "3- Makine g\\U+00FC\\U+00E7leri bilinmedi\\U+011Finden \\U+00FCretim alan\\U+0131nda 60 W/m\\U+00B2 kabul edilmi\\U+015F, bara kanal\\U+0131 ile esnek da\\U+011F\\U+0131t\\U+0131m \\U+00F6ng\\U+00F6r\\U+00FClm\\U+00FC\\U+015Ft\\U+00FCr." "4- Yang\\U+0131n pompas\\U+0131 ADP ana \\U+015Falteri \\U+00D6NCES\\U+0130NDEN ayr\\U+0131 devre, aM sigorta ve FE180/E90 yang\\U+0131na dayan\\U+0131kl\\U+0131 kablo ile beslenir (TS EN 12845)." "5- Yang\\U+0131n pompas\\U+0131 panosu ayr\\U+0131ca jenerat\\U+00F6r \\U+00E7\\U+0131k\\U+0131\\U+015F\\U+0131ndan (ATS \\U+00F6ncesi) FE180 kablo ile yedeklenir; YPP i\\U+00E7inde \\U+015Febeke/jenerat\\U+00F6r transfer \\U+015Falteri (TS-YP) ve yumu\\U+015Fak yol verici bulunur." "5a- \\U+0130dari b\\U+00F6l\\U+00FCm panolar\\U+0131 ADP i\\U+00E7indeki ATS sonras\\U+0131 acil baradan (jenerat\\U+00F6r destekli) beslenir." "6- 16 mm\\U+00B2 \\U+00FCzeri beslemelerde ayr\\U+0131 PE iletkeni \\U+00E7ekilir (TN-S, TS HD 60364-5-54)." "6a- Ka\\U+00E7ak ak\\U+0131m korumas\\U+0131 TS HD 60364-4-41 ve EMO proje esaslar\\U+0131na g\\U+00F6re kademelidir: ADP toroid KAKR (yang\\U+0131n koruma, gecikmeli) \\U+2192 tali pano giri\\U+015Fi 300 mA S tipi \\U+2192 son devre 30 mA." "6b- K\\U+0131sa devre ak\\U+0131mlar\\U+0131 trafo empedans\\U+0131 ve kablo empedanslar\\U+0131 ile hesaplanm\\U+0131\\U+015Ft\\U+0131r; \\U+015Falter kesme kapasiteleri (Icu) tablodaki Ik3 de\\U+011Ferinden b\\U+00FCy\\U+00FCk se\\U+00E7ilecektir." "7- Trafo merkezi ve OG tesisleri ayr\\U+0131 bir OG projesi ile OSB / da\\U+011F\\U+0131t\\U+0131m \\U+015Firketi onay\\U+0131na sunulacakt\\U+0131r."))
   ("P" "CLD-P2-KAK-PAFTA" T 10.0 ((121580.5 -135587.3) (127910.0 -135587.3) (127910.0 -131382.3) (121580.5 -131382.3)))
   ("P" "CLD-P2-KAK-PAFTA" nil 6.0 ((121580.5 -134837.3) (127910.0 -134837.3)))
   ("T" "CLD-P2-KAK-YAZI" 121680.5 -135027.3 70.0 0 "HESAP TABLOLARI, CETVELLER VE NOTLAR")
   ("T" "CLD-P2-KAK-YAZI" 121680.5 -135187.3 40.0 0 "KUVVETL\\U+0130 AKIM - G\\U+00DC\\U+00C7 DA\\U+011EITIM PROJES\\U+0130  -  \\U+00D6l\\U+00E7eksiz")
   ("P" "CLD-P2-KAK-PAFTA" T 6.0 ((125410.0 -135567.3) (127910.0 -135567.3) (127910.0 -134857.3) (125410.0 -134857.3)))
   ("T" "CLD-P2-KAK-YAZI" 125440.0 -134923.3 18.0 0 "\\U+0130\\U+015E\\U+0130N ADI")
   ("T" "CLD-P2-KAK-YAZI" 126030.0 -134923.3 20.0 0 "KUVVETL\\U+0130 AKIM - G\\U+00DC\\U+00C7 DA\\U+011EITIM PROJES\\U+0130")
   ("L" "CLD-P2-KAK-PAFTA" 125410.0 -134958.8 127910.0 -134958.8)
   ("T" "CLD-P2-KAK-YAZI" 125440.0 -135024.7 18.0 0 "YAPI SAH\\U+0130B\\U+0130")
   ("T" "CLD-P2-KAK-YAZI" 126030.0 -135024.7 20.0 0 "BROSCO \\U+0130THALAT \\U+0130HRACAT VE T\\U+0130CARET ANON\\U+0130M \\U+015E\\U+0130RKET\\U+0130")
   ("L" "CLD-P2-KAK-PAFTA" 125410.0 -135060.2 127910.0 -135060.2)
   ("T" "CLD-P2-KAK-YAZI" 125440.0 -135126.1 18.0 0 "ADRES")
   ("T" "CLD-P2-KAK-YAZI" 126030.0 -135126.1 20.0 0 "YUKARI MAHALLE / KEMALPA\\U+015EA / \\U+0130ZM\\U+0130R  -  Ada: ......  Parsel: 2")
   ("L" "CLD-P2-KAK-PAFTA" 125410.0 -135161.6 127910.0 -135161.6)
   ("T" "CLD-P2-KAK-YAZI" 125440.0 -135227.6 18.0 0 "PAFTA ADI")
   ("T" "CLD-P2-KAK-YAZI" 126030.0 -135227.6 20.0 0 "HESAP TABLOLARI VE NOTLAR")
   ("L" "CLD-P2-KAK-PAFTA" 125410.0 -135263.1 127910.0 -135263.1)
   ("T" "CLD-P2-KAK-YAZI" 125440.0 -135329.0 18.0 0 "\\U+00D6L\\U+00C7EK / TAR\\U+0130H / PAFTA NO")
   ("T" "CLD-P2-KAK-YAZI" 126030.0 -135329.0 20.0 0 "\\U+00D6l\\U+00E7eksiz   |   19.10.2026   |   04-03")
   ("L" "CLD-P2-KAK-PAFTA" 125410.0 -135364.5 127910.0 -135364.5)
   ("T" "CLD-P2-KAK-YAZI" 125440.0 -135430.4 18.0 0 "PROJE M\\U+00DCELL\\U+0130F\\U+0130")
   ("T" "CLD-P2-KAK-YAZI" 126030.0 -135430.4 20.0 0 "Elektrik M\\U+00FChendisi - Ad\\U+0131 Soyad\\U+0131: ..............................")
   ("L" "CLD-P2-KAK-PAFTA" 125410.0 -135465.9 127910.0 -135465.9)
   ("T" "CLD-P2-KAK-YAZI" 125440.0 -135531.8 18.0 0 "ODA S\\U+0130C\\U+0130L / SMM NO")
   ("T" "CLD-P2-KAK-YAZI" 126030.0 -135531.8 20.0 0 "EMO Sicil No: ............   SMM Belge No: ............   \\U+0130mza: ............")
   ("L" "CLD-P2-KAK-PAFTA" 126000.0 -135567.3 126000.0 -134857.3)))))

(defun c:CLD_P2_KUVVETLIAKIM ( / *error* olderr)
  (setq *error* cld:err)
  (setq *cld-u* 100.0 *cld-ext* (list 0.0 0.0 1.0))
  (cld:begin "CLD-P2-KAK-*")
  (cld:unlock "CLD-P2-KAK-*")
  (cld:unlock "CLD-KAK-*")
  (cld:clear "CLD-KAK-*")
  (cld:ops-p2_kuvvetli_akim-layers)
  (cld:clear "CLD-P2-KAK-*")
  (cld:def-symbols)
  (cld:ops-p2_kuvvetli_akim-1)
  (cld:ops-p2_kuvvetli_akim-2)
  (cld:end "CLD: Parsel 2 - KUVVETLI AKIM - GUC DAGITIM PROJESI cizildi")
  (princ))

(if (cld:wrong-dwg "2" (list "3" "4" "5"))
  (princ "\nCLD UYARI: Bu dosya PARSEL 2 icindir; acik cizim baska bir parsele ait gorunuyor. Yine de cizmek icin CLD_P2_KUVVETLIAKIM yazin.")
  (progn (princ "\nCLD: Parsel 2 KUVVETLI_AKIM yukleniyor, cizim olusturuluyor...") (c:CLD_P2_KUVVETLIAKIM)))
(princ "\nCLD: Yeniden cizmek icin komut: CLD_P2_KUVVETLIAKIM")
(princ)
